# vim: set ft=python :
# vim: set expandtab :

from typing import Any
import logging
import math

import FreeCAD as App
import OpenSCADUtils
import Draft
from FreeCAD import Rotation

logger = logging.getLogger(__name__)
logging.basicConfig(level=logging.INFO)

class Hull:
    def __init__(self, boat_name: str):
        logger.info("start")
        label = "hull"
        self.doc = App.ActiveDocument or App.newDocument()

        dimensions = self.doc.getObjectsByLabel("dimensions")[0]
        deck_width = dimensions.get("deck_width")
        deck_height = dimensions.get("deck_height")

        self.boat = (
                self.doc.getObject(boat_name) or
                self.doc.getObjectsByLabel(boat_name))[0]
        if not self.boat:
            assert False, f"No object called {boat_name}."
        self.doc.recompute()
        self.hull = create_group(self.doc, label, element_type='PartDesign::Body')
        self.doc.recompute()
        self.boat.addObject(self.hull)
        self.doc.recompute()
        Gui.activateView('Gui::View3DInventor', True)
        Gui.activeView().setActiveObject('pdbody', self.hull)

        # Templates outlining hull shape.
        sketch_cross_section = self.doc.getObjectsByLabel('cross_section_template')[0]
        sketch_profile_deck = self.doc.getObjectsByLabel('profile_deck')[0]
        sketch_profile_keel = self.doc.getObjectsByLabel('profile_keel')[0]
        sketch_plan_deck = self.doc.getObjectsByLabel('plan_deck')[0]
        # These 2 dictate the centre of the arc used to form the curve from the top
        # of the hull deadrise to the deck.
        sketch_hull_curve_height = self.doc.getObjectsByLabel('hull_curve_height')[0]
        sketch_hull_curve_horizontal = self.doc.getObjectsByLabel('hull_curve_horizontal')[0]

        # Sizes.
        self.deck_length = get_dimension(self.doc, "deck_length")
        self.deck_width = get_dimension(self.doc, "deck_width")
        self.deck_height = get_dimension(self.doc, "deck_height")
        prow_height = get_dimension(self.doc, "prow_height")
        stern_height = get_dimension(self.doc, "stern_height")
        self.highest = max(prow_height, stern_height)
        section_count = get_dimension(self.doc, "section_count")
        self.cob_offset = get_dimension(self.doc, "cob_offset")
        highest = deck_height + max(prow_height, stern_height)
        deadrise_radius = sketch_cross_section.Geometry[0].Radius

        logger.info(f"Calculating {section_count} cross sections")

        self.cross_sections = {}
        section_pos = -self.deck_length.Value / 2
        step_len = self.deck_length.Value / (section_count - 1)
        for index in range(section_count):
            working_section_pos = section_pos
            if section_pos < -self.deck_length.Value / 2:
                working_section_pos = -self.deck_length.Value / 2
            elif section_pos > self.deck_length.Value / 2:
                working_section_pos = self.deck_length.Value / 2

            if working_section_pos <= -self.deck_length.Value / 2 + 5:
              working_section_pos += 5

            # intersect outline drawings to find section dimensions.
            intersection_plane = Part.makePlane(highest * 2, deck_width * 2, App.Vector(-deck_width, working_section_pos, 0), App.Vector(0, 1, 0))
            deck_plan_intersection = sketch_plan_deck.Shape.section(intersection_plane).Vertexes[0].X
            deck_height_intersection = sketch_profile_deck.Shape.section(intersection_plane).Vertexes[0].Z
            keel_height_intersection = sketch_profile_keel.Shape.section(intersection_plane).Vertexes[0].Z
            hull_curve_height_intersection = sketch_hull_curve_height.Shape.section(intersection_plane).Vertexes[0].Z
            hull_curve_height_intersection = max(deck_height_intersection, hull_curve_height_intersection)
            hull_curve_height_intersection = hull_curve_height_intersection
            hull_curve_horizontal_intersection = sketch_hull_curve_horizontal.Shape.section(intersection_plane).Vertexes[0].X
            #hull_curve_horizontal_intersection = min(0, hull_curve_horizontal_intersection)

            section_label = f"rib_{round(working_section_pos, 0)}"
            print(section_label, section_pos, working_section_pos, index, deck_plan_intersection)

            section = self.draw_section(
                    -deck_plan_intersection,
                    deck_height_intersection,
                    -hull_curve_horizontal_intersection,
                    hull_curve_height_intersection,
                    keel_height_intersection,
                    deadrise_radius
                    )
            if section:
                section.AttachmentOffset = App.Placement(
                        App.Vector(0, working_section_pos, 0),
                        App.Vector(1, 0, 0),
                        90)
                self.hull.addObject(section)
                self.cross_sections[section_label] = section

            section_pos += step_len

        self.loft()
        self.transom()

        Gui.updateGui()

    def draw_template(self, deck_width, deck_height, curve_width, curve_height, keel_height):
        """ Not used. Would create a base cross section template. """
        print(f"\t  {deck_width=} {deck_height=} {curve_width=} {curve_height=} {keel_height=}")
        plane = self.doc.getObjectsByLabel("XY-plane")[0]

        sketch = self.doc.addObject("Sketcher::SketchObject", "template")
        sketch.AttachmentOffset = App.Placement(App.Vector(0, 0, 0), App.Rotation(App.Vector(1, 0, 0), 90))
        sketch.AttachmentSupport = (plane, [''])
        sketch.MapMode = 'FlatFace'
        sketch.Visibility = False
        self.doc.recompute()

        origin =          App.Vector(0,               keel_height,         0)
        deadrise_mid =    App.Vector(-deck_width / 4, keel_height,         0)
        deadrise_end =    App.Vector(-deck_width / 2, deck_height / 5,     0)
        curve_mid =       App.Vector(-deck_width,     3 * deck_height / 5, 0)
        curve_top =       App.Vector(-deck_width,     deck_height,         0)
        
        upper_curve_center = App.Vector(-curve_width, curve_height, 0)
        upper_curve_radius = upper_curve_center.distanceToPoint(curve_top)

        deadrise = sketch.addGeometry(Part.Arc(origin, deadrise_mid, deadrise_end))
        upper_curve = sketch.addGeometry(Part.Arc(deadrise_end, curve_mid, curve_top))

        self.constrain_to_point(sketch, deadrise, 2, origin)
        self.constrain_to_point(sketch, upper_curve, 1, curve_top)

        self.doc.recompute()

        # Clamp deadrise center on hull center line.
        # This forces the very bottom of the curve to be horizontal.
        con = sketch.addConstraint(Sketcher.Constraint("DistanceX", deadrise, 3, 0))
        sketch.renameConstraint(con, u'force_flat_bottom')
        tan = sketch.addConstraint(Sketcher.Constraint('Tangent', deadrise, 1, upper_curve, 2))
        sketch.renameConstraint(tan, u'collinear_curves')
        self.doc.recompute()
        deadrise_radius = sketch.Geometry[deadrise].Radius

        return deadrise_radius

    def draw_section(self, deck_width, deck_height, curve_width, curve_height, keel_height, deadrise_radius):
        if abs(deck_width) < 1:
            deck_width = 1.0
            curve_width = deck_width / 4
            keel_height = deck_height - 1
        #print(f"\t  {deck_width=} {deck_height=} {curve_width=} {curve_height=} {keel_height=} {deadrise_radius=}")
        plane = self.doc.getObjectsByLabel("XY-plane")[0]

        sketch = self.doc.addObject("Sketcher::SketchObject", "cross_section")
        sketch.AttachmentOffset = App.Placement(App.Vector(0, 0, 0), App.Rotation(App.Vector(1, 0, 0), 90))
        sketch.AttachmentSupport = (plane, [''])
        sketch.MapMode = 'FlatFace'
        sketch.Visibility = False
        self.doc.recompute()

        origin =          App.Vector(0,               keel_height,         0)
        curve_top =       App.Vector(-deck_width,     deck_height,         0)
        
        upper_curve_center = App.Vector(-curve_width, curve_height, 0)
        upper_curve_radius = upper_curve_center.distanceToPoint(curve_top)

        # We already know 2 out of the 3 points that define the upper_curve: curve_mid and curve_top.
        # To work out where the 2 curves meet, we must work out the shape of the triangle governing
        # the deadrise curve.
        # We know the origin.
        # We know the deadrise_radius. This is the distance from both the origin to deadrise_center
        # and also the distance from the curve joining point and deadrise_center.
        # For the 2 curves to be collinear at their meeting point, the line perpendicular to the curves at
        # this point must go through the center point of both arcs.
        # With this we can work out the lengths of all 3 edges of the triangle governing the deadrise curve.
        #   a == origin -> deadrise_center             == deadrise_radius
        #   b == upper_curve_center -> deadrise_center == deadrise_radius - upper_curve_radius
        #   c == upper_curve_center -> origin          == upper_curve_center.distanceToPoint(origin)
        # With this we can work out the angle between b and c and use this angle combined with upper_curve_center 
        # and upper_curve_radius to work out the curve joining point.
        a = deadrise_radius
        b = deadrise_radius - upper_curve_radius
        c = upper_curve_center.distanceToPoint(origin)

        # Cosine rule:
        diviser = 2 * b * c
        if diviser < 1e-4:
            A = 0
        else:
            val = (b**2 + c**2 - a**2) / diviser
            A = 0
            if abs(val) < 1: 
                A = math.acos(val)

        c_vec = upper_curve_center - origin
        rot = Rotation(App.Vector(0, 0, 1), math.degrees(A))
        b_vec = -rot.multVec(c_vec).normalize()
        join_point = upper_curve_center + b_vec * -upper_curve_radius
        deadrise_center = upper_curve_center + b_vec * b

        axis = App.Vector(0, 0, 1)
        up = App.Vector(1, 0, 0)
        truncate_curve = False

        if join_point.y > curve_top.y or join_point.y < origin.y:
            # Top curve is entirely above the deck
            # or
            # top of top curve is narrower than widest point.
            join_point = origin + curve_top * 1e-6
            truncate_curve = True

        start_angle = -(join_point - deadrise_center).getAngle(up)
        end_angle = -(origin - deadrise_center).getAngle(up)
        
        if start_angle == end_angle or truncate_curve:
            deadrise_geometery_l = Part.LineSegment(join_point, origin)
            deadrise_geometery_r = Part.LineSegment(origin, mirror(join_point))
        else:
            deadrise_geometery_l = Part.ArcOfCircle(
                Part.Circle(deadrise_center, axis, deadrise_radius),
                start_angle, end_angle)

            # mirror to other side.
            deadrise_geometery_r = Part.ArcOfCircle(
                Part.Circle(mirror(deadrise_center), axis, deadrise_radius),
                math.pi - end_angle, math.pi - start_angle)
        deadrise_l = sketch.addGeometry(deadrise_geometery_l)
        deadrise_r = sketch.addGeometry(deadrise_geometery_r)
        self.constrain_to_point(sketch, deadrise_l, 1, join_point)
        self.constrain_to_point(sketch, deadrise_l, 2, origin)
        self.constrain_to_point(sketch, deadrise_r, 2, mirror(join_point))
        self.constrain_to_point(sketch, deadrise_r, 1, origin)

        start_point = curve_top
        end_point = join_point
        start_angle = -(curve_top - upper_curve_center).getAngle(up)
        end_angle = -(join_point - upper_curve_center).getAngle(up)
        circle = Part.Circle(upper_curve_center, axis, upper_curve_radius)
        upper_curve_geometry_l = Part.ArcOfCircle(circle, start_angle, end_angle)
        circle = Part.Circle(mirror(upper_curve_center), axis, upper_curve_radius)
        upper_curve_geometry_r = Part.ArcOfCircle(circle, math.pi - end_angle, math.pi - start_angle)

        upper_curve_l = sketch.addGeometry(upper_curve_geometry_l)
        upper_curve_r = sketch.addGeometry(upper_curve_geometry_r)
        self.constrain_to_point(sketch, upper_curve_l, 1, start_point)
        self.constrain_to_point(sketch, upper_curve_l, 2, end_point)
        self.constrain_to_point(sketch, upper_curve_r, 2, mirror(start_point))
        self.constrain_to_point(sketch, upper_curve_r, 1, mirror(end_point))

        start_point = curve_top
        end_point = mirror(curve_top)
        deck_geometry = Part.LineSegment(start_point, end_point)
        deck = sketch.addGeometry(deck_geometry)
        self.constrain_to_point(sketch, deck, 1, start_point)
        self.constrain_to_point(sketch, deck, 2, end_point)

        return sketch

    def constrain_to_point(self, sketch, edge, point_of_edge, point):
        sketch.addConstraint(Sketcher.Constraint('DistanceX', edge, point_of_edge, -1, 1, -point.x))
        sketch.addConstraint(Sketcher.Constraint('DistanceY', edge, point_of_edge, -1, 1, -point.y))

    def loft(self):
        additive_loft = self.hull.newObject('PartDesign::AdditiveLoft', f"hull_loft")
        additive_loft.Ruled = True

        for cross_section in self.cross_sections.values():
          if not additive_loft.Profile:
            additive_loft.Profile = cross_section
          else:
            additive_loft.Sections += [cross_section]

        App.ActiveDocument.recompute()
        self.shape = additive_loft.Shape

    def transom(self):
        dimensions = self.doc.getObjectsByLabel("dimensions")[0]
        stern_height = dimensions.get("stern_height")
        deck_width = dimensions.get("deck_width")
        deck_length = dimensions.get("deck_length")
        transom_angle = dimensions.get("transom_angle")
        transom_overlap = dimensions.get("transom_overlap")

        if transom_overlap.Value <= 0:
          return

        transom_mask = Part.makeBox(deck_width, transom_overlap * 3, stern_height * 3, 
                                    App.Vector(-deck_width / 2, deck_length / 2, -stern_height),
                                    App.Vector(0, 0, 1))
        transom_mask = transom_mask.rotate(App.Vector(0, deck_length / 2, stern_height),
                                           App.Vector(1, 0, 0),
                                           -transom_angle)

        to_cut = self.hull.newObject('PartDesign::Boolean','Boolean')
        to_cut.Type = "Cut"
        to_cut.addObjects([Part.show(transom_mask, "transom_mask")])
        App.ActiveDocument.recompute()

    def bouancy_report(self):
        dimensions = self.doc.getObjectsByLabel("dimensions")[0]
        target_weight = dimensions.get("target_weight").Value
        self.water_angles = create_group(self.doc, "water_angles")
        target_volume = round(self.hull.Shape.Volume * 1e-6 / target_weight)
        for heel_angle in range(0, 36, 5):
            print(f"Drawing waterline at: {target_volume=} and {heel_angle=}.")
            height, wet_hull, water = self.bouancy_boolean_search(heel_angle, target_volume)
            wet_volume = round(wet_hull.Volume * 1e-6)
            
            center_of_bouancy = wet_hull.CenterOfGravity
            cob = Part.show(Part.Vertex(center_of_bouancy), f"COB_{heel_angle}")
            self.water_angles.addObject(cob)

            print(f"  {wet_volume=}, {center_of_bouancy.y=}")

            wet_hull = Part.show(wet_hull, f"wet_hull_{heel_angle}")
            wet_hull.Visibility = False
            self.water_angles.addObject(wet_hull)
            water = Part.show(water, f"water_{heel_angle}")
            water.Visibility = False
            self.water_angles.addObject(water)

    def bouancy_boolean_search(self, angle, target_volume):
      dimensions = self.doc.getObjectsByLabel("dimensions")[0]
      deck_height = dimensions.get("deck_height").Value

      last_height = deck_height / 4
      height = last_height * 1.1
      last_achieved_volume, _, _ = self.at_angle(angle, last_height)
      while True:
        achieved_volume, wet_hull, water = self.at_angle(angle, height)
        #print(f"  {height=} {last_achieved_volume=} {achieved_volume=}")

        if abs(achieved_volume - target_volume) <= 5:
          return height, wet_hull, water

        diff_volume = achieved_volume - last_achieved_volume
        if abs(diff_volume) < 1e-3:
          if achieved_volume > target_volume:
            print("*+")
            mod_height = -1e-3
          else:
            print("*-")
            mod_height = 1e-3
        else:
          mod_height = (height - last_height) * (target_volume - last_achieved_volume) / (diff_volume * 2)

        last_achieved_volume = achieved_volume
        last_height = height
        height += mod_height

    def at_angle(self, angle, height):
        rotation_axis = App.Vector(0, 1, 0)
        water_shape = App.Vector(10000, 10000, 10000)
        water_offset = App.Vector(-5000, -5000, -10000 + height)
        water = Part.makeBox(water_shape.x, water_shape.y, water_shape.z,
                             water_offset)

        water.rotate(App.Vector(0, 0, 0), rotation_axis, angle)
        wet_hull = self.hull.Shape.common(water)
        wet_volume = wet_hull.Volume * 1e-6
        return (wet_volume, wet_hull, water)


def mirror(point):
    """ Mirror about the center line. """
    return App.Vector(-point.x, point.y, point.z)

def get_dimension(doc, label: str) -> Any:
    dimensions = doc.getObjectsByLabel('dimensions')[0]
    return dimensions.get(label)

def has_object_by_label(doc, label):
  return label in [o.Label for o in FreeCAD.ActiveDocument.Objects]

def remove_group(doc, name):
  if not has_object_by_label(doc, name):
    return

  groups = doc.getObjectsByLabel(name)
  if not isinstance(groups, list):
    groups = [groups]

  for group in groups:
    if group:
      try:
        OpenSCADUtils.removesubtree(group)
      except TypeError:
        group.removeObjectsFromDocument()
        doc.getObject(group.Name).removeObjectsFromDocument()
        doc.removeObject(group.Name)

def create_group(doc, name, element_type='App::DocumentObjectGroup'):
  remove_group(doc, name)
  doc.recompute()
  new = doc.addObject(element_type, name)
  doc.recompute()
  return new


hull = Hull("boat")
hull.bouancy_report()
