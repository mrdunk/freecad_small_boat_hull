# vim: set ft=python :
# vim: set expandtab :

import math
import time
import cProfile

import Draft
import FreeCADGui
import OpenSCADUtils
import TechDraw
import Part
import DraftGeomUtils
import draftgeoutils
import importDXF
import MeshPart
from FreeCAD import Units

class Slice_Base(list):
  intersection_count: int
  plane = App.Vector(0, 0, 0)
  lowest_point = 0
  section_positions = []

  def __init__(self, doc, hull_body, intersection_count = None, section_positions = []):
    print(f"Calculating {self.__class__.__name__}")
    self.doc = doc
    self.hull_body = hull_body
    self.intersection_count = intersection_count
    self.section_positions = section_positions
    bound_box = self.hull_body.Shape.BoundBox
    self.lowest_point = bound_box.ZMin

    self.slice()

  def _setup_section_positions(self):
    bound_box = self.hull_body.Shape.BoundBox

    if self.plane.x:
      self.slice_start = bound_box.XMin
      slice_range = bound_box.XLength
    elif self.plane.y:
      self.slice_start = bound_box.YMin
      slice_range = bound_box.YLength
    elif self.plane.z:
      self.slice_start = bound_box.ZMin
      slice_range = bound_box.ZLength
    self.slice_width = slice_range / (self.intersection_count + 1)

    self.section_positions = [
          self.slice_start + (i * self.slice_width) + 0.1
          for i in range(self.intersection_count + 1)
        ]

  def slice(self):
    if not self.section_positions:
      self._setup_section_positions()

    slices = self.hull_body.Shape.slices(self.plane, self.section_positions)
    print(f"{len(slices.Wires)} sections drawn for the {self.plane} axis")
    for slice in slices.Wires:
      self += self.slice_to_edges(slice)

  def slice_to_edges(self, slice):
    all_edges = []
    for edge in slice.Edges:
      candiate = self.filter_edge(edge)
      if candiate:
        all_edges.append(candiate)

    wires = []
    for wire in Part.sortEdges(all_edges):
      try:
        wires.append(Part.Wire(wire))
      except Part.OCCError:
        # Not sure why the edges sometimes don't join up. They look fine when displayed.
        pass
    return wires

  @classmethod
  def filter_edge(cls, edge):
    start_point = edge.firstVertex()
    end_point = edge.lastVertex()

    if start_point.X < -0.0001 or end_point.X < -0.0001:
      return None

    return edge

  def longest_element(self):
    longest = None
    for wire in self:
      if longest is None or wire.Length > longest.Length:
        longest = wire

    return longest


class Slice_CrossSection(Slice_Base):
  plane = App.Vector(0, 1, 0)

  def _setup_section_positions(self):
    bound_box = self.hull_body.Shape.BoundBox

    if self.section_positions:
      pass
    elif self.intersection_count:
      slice_range = bound_box.YLength
      slice_width = slice_range / (self.intersection_count + 1)
      slice_end = bound_box.YMax - slice_width / 4

      self.slice_start = bound_box.YMin + slice_width / 4 + 1
      self.slice_width = abs(self.slice_start - slice_end) / (self.intersection_count - 1)

      self.section_positions = [
            self.slice_start + (i * self.slice_width) + 0.1
            for i in range(self.intersection_count + 1)
          ]
    else:
      dimensions = doc.getObjectsByLabel("dimensions")[0]
      index = 0
      self.section_positions = []
      while True:
        rib_pos_label = f"rib_positions_{index}"
        try:
          rib_position = dimensions.get(rib_pos_label)
        except ValueError:
          break
        self.section_positions.append(rib_position)
        index += 1

class Slice_Waterline(Slice_Base):
  plane = App.Vector(0, 0, 1)


class Slice_Profile(Slice_Base):
  plane = App.Vector(1, 0, 0)


class Slice_Diagonals(Slice_Base):
  plane = App.Vector(1, 0, 1)

  def __init__(self, doc, hull_body, ribs: Slice_CrossSection, intersection_count = None, section_positions = []):
    self.ribs = ribs
    super().__init__(doc, hull_body, intersection_count, section_positions)

  @classmethod
  def iretrate_diagonal_params(cls):
    dimensions = doc.getObjectsByLabel("dimensions")[0]
    index = 0
    while True:
      angle_label = f"diagonal_angles_{index}"
      height_label = f"diagonal_heights_{index}"
      try:
        diagonal_angle = dimensions.get(angle_label)
        diagonal_height = dimensions.get(height_label)
      except ValueError:
        break
      yield(diagonal_angle, diagonal_height)
      index += 1

  def iterate_positions(self):
    dimensions = doc.getObjectsByLabel("dimensions")[0]

    if not self.section_positions and not self.intersection_count:
      index = 0
      self.section_positions = []
      while True:
        angle_label = f"diagonal_angles_{index}"
        height_label = f"diagonal_heights_{index}"
        try:
          diagonal_angle = dimensions.get(angle_label)
          diagonal_height = dimensions.get(height_label)
        except ValueError:
          break
        self.section_positions.append((diagonal_angle, diagonal_height))
        index += 1

    if self.section_positions:
      for angle, dist in self.section_positions:
        yield angle, dist
    else:
      assert self.intersection_count is not None
      angle = 90
      slice_angle_step = angle / self.intersection_count / 1.8

      for _, position in self.iterate_longest_rib():
        angle -= slice_angle_step
        if angle <= 0:
          break
        dist = position.z - position.x / math.tan(math.radians(-angle))
        yield angle, dist

  def slice(self):
    """
    The Diagonals don't follow the same pattern as the other perspectives.
    The plane changes angle with each slice.
    """
    for angle, dist in self.iterate_positions():
      print(f"Calculating diagonal. angle: {round(angle, 2)}  height: {round(dist, 2)}")

      plane = App.Vector(math.cos(math.radians(angle)), 0, math.sin(math.radians(angle)))
      slices = self.hull_body.Shape.slice(plane, math.sin(math.radians(angle)) * dist)
      #Part.show(slices[0], "slices")
      if not slices:
        continue

      for slice in slices:
        wires = self.slice_to_edges(slice)
        if len(wires) > 1:
          longest = None
          for wire in wires:
            if longest is None or wire.Length > longest.Length:
              longest = wire
          wires = [longest]

        self += wires

  def iterate_longest_rib(self):
    rib = self.ribs.longest_element()
    #Part.show(rib, "rib")
    part_length = rib.Length / self.intersection_count
    rib_parts = rib.discretize(Distance = part_length)
    distance = 0
    for index, position in enumerate(rib_parts):
      yield (rib, position)
      distance += part_length


  @classmethod
  def filter_edge(cls, edge):
    # Filter edges ending when crossing over to other side of hull.
    start_point = edge.firstVertex()
    end_point = edge.lastVertex()
    if start_point.X < -0.0001 or end_point.X < -0.0001:
      return None

    # Filter intersections with deck.
    sketch = doc.getObjectsByLabel('profile_deck')[0]
    for sketch_edge in sketch.Shape.Edges:
      for point in edge.Vertexes:
        point = point.Point
        point.x = 0
        point = Part.Vertex(point)
        common = point.common([sketch_edge])
        if common.Vertexes:
          return None

    #Part.show(edge)
    return edge


class View_Wireframe_Base:
  """
  Base class to display wireframe of hull.
  """
  name: str = "base_class"

  def __init__(self, parent_name: str, doc, hull_body, data: Slice_Base):
    self.name = f"{parent_name}__{self.plan_name}"
    self.wireframe_name = f"{parent_name}__{self.wireframe_name}"
    self.doc = doc
    self.hull_body = hull_body
    self.data = data

    if not self._calculate():
      remove_group(doc, self.wireframe_name)
      return

    self.create_blank_sketch()

    for slice_index, slice in enumerate(self.data):
      self.parse_slice(slice, slice_index)

    for shape in self.wireframe.OutList:
      FreeCADGui.getDocument(self.doc.Name).getObject(shape.Name).LineColor = self.colour
      FreeCADGui.getDocument(self.doc.Name).getObject(shape.Name).PointColor = self.colour

    self._cleanup()

  def _cleanup(self):
    Gui.Selection.clearSelection()
    addSelection(self.doc, self.wireframe_name)
    dimensions = doc.getObjectsByLabel("dimensions")[0]
    if int(dimensions.get("show_wireframe")):
      Gui.runCommand('Std_ShowSelection', 0)
    else:
      Gui.runCommand('Std_HideSelection', 0)

  def _calculate(self):
    dimensions = doc.getObjectsByLabel("dimensions")[0]
    return dimensions.get("calculate_wireframe")

  def create_blank_sketch(self):
    self.wireframe = create_group(self.doc, self.wireframe_name)

  def parse_slice(self, slice, slice_index):
    if not slice:
      return
    new_object = Part.show(slice)
    self.wireframe.addObjects([new_object])


class View_Wireframe_Body(View_Wireframe_Base):
  plan_name = "plan_body"
  wireframe_name = "wireframe_body"

  plan_offset = App.Vector(+2000.0, 0.0, 0.0)
  colour_fore = (255, 0, 0)
  colour_aft = (255, 255, 0)
  colour = (255, 0, 0)

  def __init__(self, parent_name: str, doc, hull_body, data: Slice_Base):
    super().__init__(parent_name, doc, hull_body, data)

    for shape in self.wireframe_fore.OutList:
      FreeCADGui.getDocument(self.doc.Name).getObject(shape.Name).LineColor = self.colour_fore
      FreeCADGui.getDocument(self.doc.Name).getObject(shape.Name).PointColor = self.colour_fore

    for shape in self.wireframe_aft.OutList:
      FreeCADGui.getDocument(self.doc.Name).getObject(shape.Name).LineColor = self.colour_aft
      FreeCADGui.getDocument(self.doc.Name).getObject(shape.Name).PointColor = self.colour_aft

    self._later_cleanup()

  def _cleanup(self):
    return

  def _later_cleanup(self):
    Gui.Selection.clearSelection()
    addSelection(self.doc, self.wireframe_fore.Name)
    addSelection(self.doc, self.wireframe_aft.Name)
    dimensions = doc.getObjectsByLabel("dimensions")[0]
    if int(dimensions.get("show_wireframe")):
      Gui.runCommand('Std_ShowSelection', 0)
    else:
      Gui.runCommand('Std_HideSelection', 0)

  def _calculate(self):
    """ Always calculate this sub class. """
    return True

  def create_blank_sketch(self):
    self.wireframe_fore = create_group(self.doc, f"{self.wireframe_name}_fore")
    self.wireframe_aft = create_group(self.doc, f"{self.wireframe_name}_aft")
    self.wireframe = self.wireframe_fore

  def parse_slice(self, slice, slice_index):
    if slice_index > len(self.data) / 2:
      self.wireframe = self.wireframe_fore
      self.colour = self.colour_fore
    else:
      self.wireframe = self.wireframe_aft
      self.colour = self.colour_aft

    super().parse_slice(slice, slice_index)


class View_Wireframe_Waterline(View_Wireframe_Base):
  plan_name = "plan_waterline"
  wireframe_name = "wireframe_waterline"
  plan_offset = App.Vector(+4000.0, 0.0, 0.0)
  colour = (0, 255, 0)


class View_Wireframe_Profile(View_Wireframe_Base):
  plan_name = "plan_profile"
  wireframe_name = "wireframe_profile"
  plan_offset = App.Vector(+6000.0, 0.0, 0.0)
  colour = (0, 0, 255)


class View_Wireframe_Diagonals(View_Wireframe_Base):
  plan_name = "plan_diagonal"
  wireframe_name = "wireframe_diagonal"
  plan_offset = App.Vector(+8000.0, 0.0, 0.0)
  colour = (200, 200, 200)


class Plans:
  def __init__(self, doc, parent_name: str, lowest_point: float):
    self.doc = doc
    self.lowest_point = lowest_point

    plan_profile_name = f"{parent_name}__plan_profile"
    plan_body_name = f"{parent_name}__plan_body"
    plan_waterline_name = f"{parent_name}__plan_waterline"

    dimensions = doc.getObjectsByLabel("dimensions")[0]
    if not dimensions.get("calculate_plans"):
      remove_group(self.doc, plan_profile_name)
      remove_group(self.doc, plan_body_name)
      remove_group(self.doc, plan_waterline_name)
      return

    group_profile = create_group(doc, plan_profile_name)
    group_body = create_group(doc, plan_body_name)
    group_waterline = create_group(doc, plan_waterline_name)

    offset_plan_profile = 2000
    offset_plan_body = 3000
    offset_plan_waterline = 4500

    label = f"{parent_name}__wireframe_profile"
    if has_object_by_label(doc, label):
      for shapes in self.doc.getObjectsByLabel(label):
        for shape in shapes.OutList:
          self.draw_line(shape.Shape, App.Vector(1, 0, 0), offset_plan_profile, group_profile, True, False)
          self.draw_line(shape.Shape, App.Vector(0, 1, 0), offset_plan_body, group_body, False, False)
          self.draw_line(shape.Shape, App.Vector(0, 1, 0), offset_plan_body, group_body, False, True)
          self.draw_line(shape.Shape, App.Vector(0, 0, 1), offset_plan_waterline, group_waterline, False, False)
          self.draw_line(shape.Shape, App.Vector(0, 0, 1), offset_plan_waterline, group_waterline, False, True)

    label = f"{parent_name}__wireframe_body_fore"
    if has_object_by_label(doc, label):
      for shapes in self.doc.getObjectsByLabel(label):
        for shape in shapes.OutList:
          self.draw_line(shape.Shape, App.Vector(1, 0, 0), offset_plan_profile, group_profile, False, False)
          self.draw_line(shape.Shape, App.Vector(0, 1, 0), offset_plan_body, group_body, True, False)
          self.draw_line(shape.Shape, App.Vector(0, 0, 1), offset_plan_waterline, group_waterline, False, False)
          self.draw_line(shape.Shape, App.Vector(0, 0, 1), offset_plan_waterline, group_waterline, False, True)

    label = f"{parent_name}__wireframe_body_aft"
    if has_object_by_label(doc, label):
      for shapes in self.doc.getObjectsByLabel(label):
        for shape in shapes.OutList:
          self.draw_line(shape.Shape, App.Vector(1, 0, 0), offset_plan_profile, group_profile, False, False)
          self.draw_line(shape.Shape, App.Vector(0, 1, 0), offset_plan_body, group_body, True, True)
          self.draw_line(shape.Shape, App.Vector(0, 0, 1), offset_plan_waterline, group_waterline, False, False)
          self.draw_line(shape.Shape, App.Vector(0, 0, 1), offset_plan_waterline, group_waterline, False, True)

    label = f"{parent_name}__wireframe_waterline"
    if has_object_by_label(doc, label):
      for shapes in self.doc.getObjectsByLabel(label):
        for shape in shapes.OutList:
          self.draw_line(shape.Shape, App.Vector(1, 0, 0), offset_plan_profile, group_profile, False, False)
          self.draw_line(shape.Shape, App.Vector(0, 1, 0), offset_plan_body, group_body, False, False)
          self.draw_line(shape.Shape, App.Vector(0, 1, 0), offset_plan_body, group_body, False, True)
          self.draw_line(shape.Shape, App.Vector(0, 0, 1), offset_plan_waterline, group_waterline, True, False)

    label = f"{parent_name}__wireframe_diagonal"
    if has_object_by_label(doc, label):
      for shapes in self.doc.getObjectsByLabel(label):
        for shape in shapes.OutList:
          self.draw_line(shape.Shape, App.Vector(0, 0, 1), offset_plan_waterline, group_waterline, True, True)
          self.draw_line(shape.Shape, App.Vector(0, 1, 0), offset_plan_body, group_body, False, False)
          self.draw_line(shape.Shape, App.Vector(0, 1, 0), offset_plan_body, group_body, False, True)

    self.extra(group_profile, offset_plan_profile)

    Gui.Selection.clearSelection()
    addSelection(self.doc, f"{parent_name}__plan_profile")
    addSelection(self.doc, f"{parent_name}__plan_body")
    addSelection(self.doc, f"{parent_name}__plan_waterline")
    addSelection(self.doc, f"{parent_name}__plan_diagonal")
    dimensions = doc.getObjectsByLabel("dimensions")[0]
    if int(dimensions.get("show_plans")):
      Gui.runCommand('Std_ShowSelection', 0)
    else:
      Gui.runCommand('Std_HideSelection', 0)

  def draw_line(self, shape, direction, x_pos, group, foreground: bool, mirror: bool):
    outline, _, _, _ = TechDraw.project(shape, direction)
    new = Part.show(outline, "outline")

    if direction == App.Vector(1, 0, 0):
      new.Placement = App.Placement(
          App.Vector(x_pos - self.lowest_point, 0, self.lowest_point),
          App.Vector(1, 0, 0), 180)

    if mirror:
      if direction == App.Vector(0, 1, 0):
        new.Placement = App.Placement(
            App.Vector(x_pos - self.lowest_point, 0, self.lowest_point),
            App.Vector(1, 0, 0), 180)
      elif direction == App.Vector(0, 0, 1):
        new.Placement = App.Placement(
            App.Vector(x_pos, 0, self.lowest_point),
            App.Vector(0, 1, 0), 180)
    else:
      if direction == App.Vector(0, 1, 0):
        new.Placement = App.Placement(
            App.Vector(x_pos - self.lowest_point, 0, self.lowest_point),
            App.Vector(1, 0, 0), 0)
      elif direction == App.Vector(0, 0, 1):
        new.Placement = App.Placement(
            App.Vector(x_pos, 0, self.lowest_point),
            App.Vector(0, 1, 0), 0)

    if foreground:
      FreeCADGui.getDocument(self.doc.Name).getObject(new.Name).LineWidth = 2
      FreeCADGui.getDocument(self.doc.Name).getObject(new.Name).PointSize = 2
    else:
      FreeCADGui.getDocument(self.doc.Name).getObject(new.Name).LineWidth = 1
      FreeCADGui.getDocument(self.doc.Name).getObject(new.Name).PointSize = 1

    group.addObjects([new])

  def extra(self, group, offset_plan_profile):
    sketches = [
        doc.getObjectsByLabel('dagger_board')[0],
        #doc.getObjectsByLabel('rudder')[0],
        ]

    for sketch in sketches:
      direction = App.Vector(1, 0, 0)
      shape = sketch.Shape

      outline, _, _, _ = TechDraw.project(shape, direction)
      new = Part.show(outline, "outline")
      new.Placement = App.Placement(
          App.Vector(offset_plan_profile, 0, 0),
          direction, 180)

      group.addObjects([new])


class Components:
  stringers = []
  planks = []
  flat_planks = {}
  keelson = None
  stringers_deep = []
  ribs = {}
  components_flat = {}
  components_bulk = {}
  figurehead = None
  plank_plans = []

  def __init__(self, doc, parent_name: str, body, diagonals: Slice_Diagonals):
    self.doc = doc
    self.parent_name = parent_name
    self.group = create_group(doc, f"{parent_name}__components")
    self.hull = body
    self.diagonals = diagonals
    ribs_data = {}
    rib_diagonal_intersections = {}
    self.stringers_group = None
    self.plans_planks_group = None
    self.solid_planks_group = None

    self.draw_stringers()
    self.draw_gunwale()

    self.draw_rudder()
    self.draw_stem()
    self.draw_stern()
    self.draw_keelson()
    self.draw_planking()
    self.draw_daggerboard_case()

    label = f"{parent_name}__wireframe_body_fore"
    if has_object_by_label(doc, label):
      for shapes in self.doc.getObjectsByLabel(label):
        for shape in shapes.OutList:
          self.index_ribs(shape.Shape, ribs_data)

    label = f"{parent_name}__wireframe_body_aft"
    if has_object_by_label(doc, label):
      for shapes in self.doc.getObjectsByLabel(label):
        for shape in shapes.OutList:
          self.index_ribs(shape.Shape, ribs_data)

    self.rib_group = create_group(doc, "ribs")
    self.group.addObjects([self.rib_group])

    for y_pos in sorted(ribs_data.keys(), key = lambda val: int(val)):
      rib_index, wire = ribs_data[y_pos]
      if rib_index < 0:
        continue
      self.draw_rib(doc, y_pos, rib_index, wire)

    self.mirror_sides()

    self.draw_deck()
    self.draw_transom()

  def index_ribs(self, shape, ribs_data):
    dimensions = doc.getObjectsByLabel("dimensions")[0]

    y_pos = str(round(shape.BoundBox.YMin))

    # Work out index for rib at y_pos.
    rib_index = 0
    while True:
      rib_pos_label = f"rib_positions_{rib_index}"
      try:
        rib_position = str(dimensions.get(rib_pos_label))
      except ValueError:
        rib_index = -1
        break
      if rib_position == y_pos:
        break
      rib_index += 1

    if y_pos in ribs_data :
      print(f"WARN: Duplicate ribs at {y_pos}.")

    ribs_data[y_pos] = (rib_index, shape)

  def diagonal_normals(self):
    for diagonal in self.diagonals:
      shape = Part.Shape([diagonal])
      yield (shape, self.diagonal_normal_at(shape))

  def draw_planking(self):
    dimensions = doc.getObjectsByLabel("dimensions")[0]
    prow_height = dimensions.get("prow_height")
    hull_type = dimensions.get("hull_type")
    hull_type = dimensions.get("hull_type")

    if hull_type != "plank":
      return

    self.scratch = create_group(self.doc, "scratch_planks")
    self.scratch.Visibility = False

    self.planks = []

    if self.solid_planks_group is None:
      self.plans_planks_group = create_group(doc, f"plans_planks")
      self.group.addObjects([self.plans_planks_group])
      self.plans_planks_group.Visibility = False

      self.solid_planks_group = create_group(doc, f"solid_planks")
      self.group.addObjects([self.solid_planks_group])
      self.solid_planks_group.Visibility = True

    gunwale_wire = self.gunwale_wire()
    gunwale_wire.reverse()
    diagonals_data = list(zip(self.diagonals.iterate_positions(), self.diagonal_normals())) + [((90, prow_height), (gunwale_wire, App.Vector(0, 0, 0)))]
    diagonals_data = sorted(diagonals_data, key = lambda data: data[1][0].BoundBox.ZMin)  # Sort by wire height.

    last_diagonal_wire = None
    first_plank = True  # Starts from keel (bottom).
    last_plank = False  # At top (gunwale).
    plank_count = 0
    for (angle, height), (diagonal_shape, diagonal_normal) in diagonals_data:
      height_mask = Part.makeBox(self.hull.BoundBox.XLength, self.hull.BoundBox.YLength, height * 2,
                          App.Vector(0, -self.hull.BoundBox.YLength / 2, -height))
      diagonal_shape = diagonal_shape.common(height_mask)

      diagonal_wire = Part.Wire(Part.sortEdges(diagonal_shape.Edges)[0])
      diagonal_wire = diagonal_shape.Wires[0]

      if last_diagonal_wire is not None:
        print(f"Calculating plank: {plank_count=}, {angle=}, {height=}, {first_plank=}, {last_plank=}")

        top, bottom, overlap = self.apply_plank_overlaps(diagonal_wire, last_diagonal_wire, top_overlap=not last_plank, bottom_overlap=not first_plank)

        self.flat_plank(plank_count, top, bottom, overlap)
        self.solid_plank(top, overlap)

        first_plank = False
        last_plank = (plank_count == len(diagonals_data) - 3)
        plank_count += 1

      last_diagonal_wire = diagonal_wire

  def flat_plank(self, index, top, bottom, overlap):
    dimensions = doc.getObjectsByLabel("dimensions")[0]
    plank_thickness = dimensions.get("plank_thickness")

    top = Part.show(top, "top_wire")
    bottom = Part.show(bottom, "bottom_wire")
    overlap = Part.show(overlap, "overlap_wire")

    flat_part = FreeCAD.ActiveDocument.addObject('Part::RuledSurface', 'plank_surface')
    flat_part.Curve1 = (top, [""])
    flat_part.Curve2 = (bottom, [""])

    flat_part_overlap = FreeCAD.ActiveDocument.addObject('Part::RuledSurface', 'plank_surface_overlap')
    flat_part_overlap.Curve1 = (top, [""])
    flat_part_overlap.Curve2 = (overlap, [""])

    App.ActiveDocument.recompute()

    shape = Part.getShape(flat_part, "")
    shape_overlap = Part.getShape(flat_part_overlap, "")

    mask_bow = Part.makeBox(self.hull.BoundBox.XLength, self.hull.BoundBox.YLength, self.hull.BoundBox.ZLength,
                            -App.Vector(self.hull.BoundBox.XLength / 2, self.hull.BoundBox.YLength, self.hull.BoundBox.ZMin))
    bow = shape.common(mask_bow)
    bow_overlap = shape_overlap.common(mask_bow)

    mask_stern = Part.makeBox(self.hull.BoundBox.XLength, self.hull.BoundBox.YLength, self.hull.BoundBox.ZLength,
                            -App.Vector(self.hull.BoundBox.XLength / 2, 0, self.hull.BoundBox.ZMin))
    stern = shape.common(mask_stern)
    stern_overlap = shape_overlap.common(mask_stern)

    flat_plank_bow = self.flat_plank_part(index, bow, bow_overlap, "plank_bow", plank_thickness)
    flat_plank_stern = self.flat_plank_part(index, stern, stern_overlap, "plank_stern", plank_thickness)

    self.scratch.addObject(top)
    self.scratch.addObject(bottom)
    self.scratch.addObject(overlap)
    self.scratch.addObject(flat_part)
    self.scratch.addObject(flat_part_overlap)

    top.Visibility = False
    bottom.Visibility = False
    overlap.Visibility = False
    flat_part.Visibility = False
    flat_part_overlap.Visibility = False

  def flat_plank_part(self, index, part, part_overlap, part_name, plank_thickness):
    #unwrapped = self.unwrap_shape(part, f"{part_name}_nominal")
    unwrapped_overlap = self.unwrap_shape(part_overlap, f"{part_name}_overlap")

    #self.plans_planks_group.addObject(unwrapped)
    self.plans_planks_group.addObject(unwrapped_overlap)

    #unwrapped_shape = App.ActiveDocument.getObject(unwrapped.Name)
    #unwrapped_shape = Part.getShape(unwrapped_shape, "")
    #unwrapped_shape = Part.makeFace(unwrapped_shape)
    #unwrapped_solid = unwrapped_shape.extrude(App.Vector(0, 0, 1) * plank_thickness)

    unwrapped_overlap_shape = App.ActiveDocument.getObject(unwrapped_overlap.Name)
    unwrapped_overlap_shape = Part.getShape(unwrapped_overlap_shape, "")
    unwrapped_overlap_shape = Part.makeFace(unwrapped_overlap_shape)
    unwrapped_overlap_solid = unwrapped_overlap_shape.extrude(App.Vector(0, 0, 1) * plank_thickness)

    self.flat_planks[f"{part_name}_{index}"] = unwrapped_overlap_solid

  def unwrap_shape(self, shape, name):
    feature = FreeCAD.ActiveDocument.addObject("Mesh::Feature", f"{name}_feature")
    feature.Mesh = MeshPart.meshFromShape(Shape = shape, LinearDeflection=0.1, AngularDeflection=0.523599, Relative=True)
    feature.removeNonManifolds()

    Gui.Selection.clearSelection()
    Gui.Selection.addSelection(self.doc.Name, feature.Name)
    Gui.runCommand('MeshPart_CreateFlatMesh', 0)

    unwrapped = FreeCAD.ActiveDocument.Objects[-1]
    unwrapped.Label = f"{name}_unrolled"

    self.scratch.addObject(feature)
    feature.Visibility = False
    unwrapped.Visibility = False

    return unwrapped

  def iterate_plank_edges(self, top, bottom):
    if isinstance(top, Part.Wire):
      top = [vertex.Point for vertex in top.Vertexes]
    if isinstance(bottom, Part.Wire):
      bottom = [vertex.Point for vertex in bottom.Vertexes]

    top_v_0 = None
    top_v_1 = None
    bottom_v_0 = None
    bottom_v_1 = None
    for top_v_2, bottom_v_2 in zip(top + [None], bottom + [None]):
      top_first = top_v_1
      top_last = top_v_1
      bottom_first = bottom_v_1
      bottom_last = bottom_v_1
      if top_v_0:
        top_first = top_v_0
        bottom_first = bottom_v_0
      if top_v_2:
        top_last = top_v_2
        bottom_last = bottom_v_2

      if top_v_1 and bottom_last:
        top_normal = (top_last - top_first)
        top_normal.normalize()
        bottom_normal = (bottom_last - bottom_first)
        bottom_normal.normalize()
        top_to_bottom = (top_v_1 - bottom_v_1)
        top_to_bottom.normalize()

        top_perpendicular = top_normal.cross(top_to_bottom)
        top_perpendicular.normalize()
        bottom_perpendicular = bottom_normal.cross(top_to_bottom)
        bottom_perpendicular.normalize()

        yield top_v_1, bottom_v_1, top_perpendicular, bottom_perpendicular

      top_v_0 = top_v_1
      bottom_v_0 = bottom_v_1
      top_v_1 = top_v_2
      bottom_v_1 = bottom_v_2

  def solid_plank(self, top, bottom):
    dimensions = self.doc.getObjectsByLabel("dimensions")[0]
    plank_thickness = dimensions.get(f"plank_thickness")
    cross_sections = []

    for top_v, bottom_v, top_perpendicular, bottom_perpendicular in self.iterate_plank_edges(top, bottom):
        outline = [
            Part.makeLine(top_v, bottom_v),
            Part.makeLine(bottom_v, bottom_v - bottom_perpendicular * plank_thickness),
            Part.makeLine(bottom_v - bottom_perpendicular * plank_thickness, top_v - top_perpendicular * plank_thickness),
            Part.makeLine(top_v - top_perpendicular * plank_thickness, top_v)
            ]
        plank_section_wire = Part.Wire(outline)
        plank_section_object = Part.show(plank_section_wire, "plank_section_wire")
        cross_sections.append(plank_section_object)

        plank_section_object.Visibility = False
        self.scratch.addObject(plank_section_object)
    self.loft(cross_sections)

  def loft(self, cross_sections):
    additive_loft = FreeCAD.ActiveDocument.addObject("Part::Loft", "solid_plank")
    additive_loft.Sections = cross_sections
    additive_loft.Solid = True
    additive_loft.Ruled = True

    self.solid_planks_group.addObjects([additive_loft])

    App.ActiveDocument.recompute()

    self.planks.append(additive_loft.Shape)

  def apply_plank_overlaps(self, top_wire, bottom_wire, top_overlap=True, bottom_overlap=True):
    dimensions = self.doc.getObjectsByLabel("dimensions")[0]
    lap_depth = dimensions.get(f"lap_depth")
    lap_overlap = dimensions.get(f"lap_overlap")
    rib_thickness = dimensions.get("rib_thickness")

    point_count = int(top_wire.Length / 10)

    top_wire = Part.Wire(top_wire.copy().Edges)
    bottom_wire = Part.Wire(bottom_wire.copy().Edges)
    top_wire = top_wire.discretize(Number = point_count)
    bottom_wire = bottom_wire.discretize(Number = point_count)

    top_edges = []
    bottom_edges = []
    overlap_bottom_edges = []
    last_top = None
    last_bottom = None
    last_overlap_bottom = None
    for top_v, bottom_v, top_perpendicular, bottom_perpendicular in self.iterate_plank_edges(top_wire, bottom_wire):
      overlap_bottom_v = bottom_v
      if top_overlap:
        top_v = top_v + top_perpendicular * lap_depth
      if bottom_overlap:
        bottom_v = bottom_v - bottom_perpendicular * lap_depth
        plank_vector = bottom_v - top_v
        plank_vector.normalize()
        overlap_bottom_v = bottom_v + (plank_vector * lap_overlap)

      if last_top is not None:
        top_edges.append(Part.makeLine(last_top, top_v))
        bottom_edges.append(Part.makeLine(last_bottom, bottom_v))
        overlap_bottom_edges.append(Part.makeLine(last_overlap_bottom, overlap_bottom_v))
      last_top = top_v
      last_bottom = bottom_v
      last_overlap_bottom = overlap_bottom_v

    top_edges = Part.sortEdges(top_edges)[0]
    bottom_edges = Part.sortEdges(bottom_edges)[0]
    overlap_bottom_edges = Part.sortEdges(overlap_bottom_edges)[0]

    if top_edges[0].distToShape(bottom_edges[0])[0] > top_edges[-1].distToShape(bottom_edges[0])[0]:
      bottom_edges = list(reversed(bottom_edges))
      overlap_bottom_edges = list(reversed(overlap_bottom_edges))

    new_top_wire = Part.Wire(Part.Shape(top_edges).Edges)
    new_bottom_wire = Part.Wire(Part.Shape(bottom_edges).Edges)
    overlap_bottom_wire = Part.Wire(Part.Shape(overlap_bottom_edges).Edges)

    if not bottom_overlap:
      # Bottom plank doesn't overlap keel.
      overlap_bottom_wire = overlap_bottom_wire.translate(App.Vector(1, 0, 0) * rib_thickness / 2)

    #new_top_wire = new_top_wire.cut(self.stem[0]).cut(self.stern[0]).Wires[0]
    #overlap_bottom_wire = overlap_bottom_wire.cut(self.stem[0]).cut(self.stern[0]).Wires[0]

    #Part.show(new_top_wire, "new_top_wire")
    #Part.show(new_bottom_wire, "new_bottom_wire")
    #Part.show(overlap_bottom_wire, "overlap_bottom_wire")
    return new_top_wire, new_bottom_wire, overlap_bottom_wire

  def draw_stringers(self):
    dimensions = doc.getObjectsByLabel("dimensions")[0]
    hull_type = dimensions.get("hull_type")
    stringer_width = dimensions.get("stringer_width")
    stringer_depth = dimensions.get("stringer_depth")
    accurate_stringers = dimensions.get("accurate_stringers")

    if hull_type != "sof":
      return

    hull = self.hull.copy()

    fatten = 1
    for d, normal in self.diagonal_normals():
      print(f"Drawing stringer. {normal}")
      normal.normalize()

      if get_wire_curvature(d.Wires[0]) < 0:
        d.reverse()

      # Make stringer slightly bigger than it actually is so we don't hit boolean comparison
      # issues later due to faces being in the same place on identical planes.
      pattern = clean_wire2(d.copy().Wires[0])
      pattern.translate(normal * ((stringer_width.Value + fatten) / 2))
      pattern = pattern.makeOffset2D(fatten / 2, openResult = True, fill = False)
      pattern = pattern.makeOffset2D((stringer_depth + Units.Quantity(f"{fatten}mm")), openResult = True, fill = True)
      stringer = pattern.extrude(normal * (-stringer_width.Value - fatten))

      # This deeper version of the stringer cuts the full notch out of the rib.
      # Since the plane of each stringer's curve is at a different angle to the main
      # hull it would be hard to calculate the correct shape for each notch.
      # Instead, this stringer extends all the way out of the notch so we can do a boolean cut.
      pattern_deep = clean_wire2(d.copy().Wires[0])
      pattern_deep.translate(normal * stringer_width / 2)
      pattern_deep = pattern_deep.makeOffset2D(-stringer_depth * 2, openResult = True, fill = False)
      pattern_deep = pattern_deep.makeOffset2D(stringer_depth * 3, openResult = True, fill = True)
      stringer_deep = pattern_deep.extrude(-normal * stringer_width)

      if int(accurate_stringers):
        stringer_original = stringer.copy()
        # Since the main stringer's outer face is likely to be collinear with the hull's outer surface,
        # bugs when performing the boolean operation to shape the outer face of the stringer to match
        # the outer face of the hull.
        # Instead we do the boolean operation with a copy of the deeper stringer,
        # then a 2nd boolean operation between that and the proper stringer (that has the correct dimensions).
        stringer_hull = stringer_deep.copy().common(hull)

        # This knocks off the sharp corner of the stringer that protrudes through the hull surface.
        # In real life, we'll use a plane.
        stringer = stringer_hull.common(stringer)

        if stringer.BoundBox.XLength < 1e-4 or stringer.BoundBox.XLength > 1e10:
          print("WARN: Problem with stringer geometry.")
          # Fall back to raw (un-chamfered) shape.
          stringer = stringer_original

      stringer = self.trim_transom(stringer)
      self.stringers.append(stringer)
      self.stringers_deep.append(stringer_deep)
      #Part.show(stringer, "stringer")
      #Part.show(stringer_deep, "stringer_deep")

    # set up the group to store the displayed stringers in later.
    # self.stringers will be added to the group when they are mirrored port and starboard.
    self.stringers_group = create_group(doc, f"stringers")
    self.group.addObjects([self.stringers_group])

  def gunwale_wire(self):
    profile_deck = doc.getObjectsByLabel('profile_deck')[0]
    plan_deck = doc.getObjectsByLabel('plan_deck')[0]

    # Extrude deck_profile and deck_outline out to calculate meeting point at top
    # of gunwale.
    profile_extruded = profile_deck.Shape.extrude(App.Vector(1, 0, 0) * 1000)
    plan_extruded = plan_deck.Shape.extrude(App.Vector(0, 0, 1) * 1000)
    gunwale = profile_extruded.section(plan_extruded)
    #Part.show(gunwale, "gunwale")
    return Part.Wire(gunwale.Edges)

  def draw_gunwale(self):
    #profile_deck = doc.getObjectsByLabel('profile_deck')[0]
    plan_deck = doc.getObjectsByLabel('plan_deck')[0]
    dimensions = doc.getObjectsByLabel("dimensions")[0]
    stringer_width = dimensions.get("stringer_width")
    stringer_depth = dimensions.get("stringer_depth")
    deck_length = dimensions.get("deck_length")
    rib_depth = dimensions.get("rib_depth").Value

    print("Calculating gunnel")

    mask = Part.makeBox(plan_deck.Shape.BoundBox.XLength / 2, deck_length, self.hull.BoundBox.ZLength,
                            App.Vector(0, -deck_length / 2, self.hull.BoundBox.ZMin))

    gunwale_wire = self.gunwale_wire()

    outwale_offset = gunwale_wire.copy().extrude(App.Vector(0, 0, 1) * -stringer_width)
    outwale_solid = outwale_offset.extrude(App.Vector(1, 0, 0) * -stringer_depth)
    outwale_solid = outwale_solid.common(mask)
    outwale_solid = self.trim_transom(outwale_solid)
    self.stringers.append(outwale_solid)

    outwale_deep_wire = gunwale_wire.copy().translate(App.Vector(0, 0, 1) * stringer_width.Value)
    outwale_deep_wire = outwale_deep_wire.translate(App.Vector(1, 0, 0) * stringer_depth.Value)
    outwale_deep_offset = outwale_deep_wire.extrude(App.Vector(0, 0, 1) * -stringer_width.Value * 2)
    outwale_deep_solid = outwale_deep_offset.extrude(App.Vector(1, 0, 0) * -stringer_depth.Value * 2)
    outwale_deep_offset = outwale_deep_offset.common(mask)
    self.stringers_deep.append(outwale_deep_solid)

    inwale_wire = gunwale_wire.copy().translate(App.Vector(1, 0, 0) * -(rib_depth + stringer_depth.Value / 2))
    inwale_offset = inwale_wire.extrude(App.Vector(0, 0, 1) * -stringer_width)
    inwale_solid = inwale_offset.extrude(App.Vector(1, 0, 0) * stringer_depth)
    inwale_solid = inwale_solid.common(self.hull)
    inwale_solid = self.trim_transom(inwale_solid)
    self.stringers.append(inwale_solid)

    inwale_deep_wire = gunwale_wire.copy().translate(App.Vector(1, 0, 0) * -(rib_depth + stringer_depth.Value * 1.5))
    inwale_deep_wire = inwale_deep_wire.translate(App.Vector(0, 0, 1))
    inwale_deep_offset = inwale_deep_wire.extrude(App.Vector(0, 0, 1) * -(stringer_width.Value + 1))
    inwale_deep_solid = inwale_deep_offset.extrude(App.Vector(1, 0, 0) * stringer_depth * 2)
    inwale_deep_solid = inwale_deep_solid.common(mask)
    self.stringers_deep.append(inwale_deep_solid)

    #Part.show(outwale_solid, "outwale_solid")
    #Part.show(outwale_deep_solid, "outwale_deep_solid")

    if self.stringers_group is None:
      self.stringers_group = create_group(doc, f"stringers")
      self.group.addObjects([self.stringers_group])

  def draw_rib(self, doc, rib_position: float, rib_index: int, rib_wire: Part.Wire):
    dimensions = doc.getObjectsByLabel("dimensions")[0]
    hull_type = dimensions.get("hull_type")
    rib_type = dimensions.get(f"rib_type_{rib_index}")

    if rib_type == "skip":
      return

    print(f"New rib: {rib_position=}, {rib_index=}, {rib_type=}")

    if hull_type == "plank":
      self.draw_rib_planked(doc, rib_position, rib_index, rib_wire)
    else:
      self.draw_rib_sof(doc, rib_position, rib_index, rib_wire)

  def draw_rib_planked(self, doc, rib_position: float, rib_index: int, rib_wire: Part.Wire):
    profile_deck = doc.getObjectsByLabel('profile_deck')[0]
    plan_deck = doc.getObjectsByLabel('plan_deck')[0]

    dimensions = doc.getObjectsByLabel("dimensions")[0]
    rib_thickness = dimensions.get("rib_thickness").Value
    rib_depth = dimensions.get("rib_depth").Value
    rib_bulkhead_depth = dimensions.get("rib_bulkhead_depth").Value
    rib_thwart_depth = dimensions.get("rib_thwart_depth").Value
    brace_width = dimensions.get("brace_width").Value
    brace_width_narrow = dimensions.get("brace_width_narrow").Value
    rib_chamfer_radius = dimensions.get("rib_chamfer_radius")
    rib_chamfer_radius_narrow = dimensions.get("rib_chamfer_radius_narrow")
    rib_outside_relief = dimensions.get("rib_outside_relief")
    thwart_height = dimensions.get("thwart_height").Value
    low_thwart_height = dimensions.get("low_thwart_height").Value
    deck_width = dimensions.get("deck_width")
    deck_height = dimensions.get("deck_height")
    rib_type = dimensions.get(f"rib_type_{rib_index}")
    lap_depth = dimensions.get(f"lap_depth")

    if rib_type == "bulkhead":
      rib_depth = rib_bulkhead_depth

    rib_plane = Part.Plane(App.Vector(0, int(rib_position), 0), App.Vector(0, 1, 0))

    rib_vertexes = [
        App.Vector(0, int(rib_position), rib_wire.BoundBox.ZMin),
        ]

    # Get shapes of intersections between diagonals and rib.
    last_point = None
    for diagonal in sorted(self.diagonals, key = lambda diagonal: diagonal.BoundBox.ZMin):
      intersection = diagonal.Wires[0].section(rib_plane)
      if intersection.Vertexes:
        point = intersection.Vertexes[0].Point
        if last_point is None:
          rib_vertexes.append(point)
        else:
          plank_normal = (point - last_point)
          plank_normal.normalize()
          plank_perpendicular = App.Vector(plank_normal.z, plank_normal.y, -plank_normal.x)
          plank_perpendicular.normalize()
          rib_vertexes.append(point - plank_perpendicular * lap_depth)
          rib_vertexes.append(point + plank_perpendicular * lap_depth)
        last_point = point
    # Add gunwale vertex.
    rib_vertexes.append(App.Vector(rib_wire.BoundBox.XMax, int(rib_position), rib_wire.BoundBox.ZMax))

    rib_edges = []
    last_verex = None
    first_vertex = None
    for rib_vertex in rib_vertexes:
      if last_verex:
          rib_edges.append(Part.LineSegment(last_verex, rib_vertex))
      last_verex = rib_vertex
      if not first_vertex:
        first_vertex = rib_vertex

    outer_wire = Part.Wire(Part.Shape(rib_edges).Edges)
    inner_wire = rib_wire.makeOffset2D(-rib_depth, openResult = True)

    rib_wire_mask = Part.makeBox(outer_wire.BoundBox.XLength * 2, 2, outer_wire.BoundBox.ZLength - 1e-1,
                                   App.Vector(0, outer_wire.BoundBox.YMax, outer_wire.BoundBox.ZMin))
    outer_wire = outer_wire.common(rib_wire_mask).Wires[0]
    inner_wire = inner_wire.common(rib_wire_mask).Wires[0]

    top_edge = Part.LineSegment(outer_wire.OrderedVertexes[-1].Point, inner_wire.OrderedVertexes[0].Point)
    bottom_edge = Part.LineSegment(outer_wire.OrderedVertexes[0].Point, inner_wire.OrderedVertexes[-1].Point)
    rib_edges = outer_wire.Edges + [top_edge] + inner_wire.Edges + [bottom_edge]
    rib_wire = Part.Wire(Part.Shape(rib_edges).Edges)
    rib_face = Part.makeFace([rib_wire])
    #Part.show(rib_face, "rib_face")

    thwart_mask = Part.makeBox(outer_wire.BoundBox.XLength * 2, 2, thwart_height - outer_wire.BoundBox.ZMin,
                               App.Vector(0, outer_wire.BoundBox.YMax, outer_wire.BoundBox.ZMin))
    thwart_outer_wire = outer_wire.common(thwart_mask).Wires[0]

    thwart_top_edge = Part.LineSegment(thwart_outer_wire.OrderedVertexes[-1].Point,
                                       App.Vector(0, thwart_outer_wire.BoundBox.YMax, thwart_height))
    thwart_center_edge = Part.LineSegment(App.Vector(0, thwart_outer_wire.BoundBox.YMax, thwart_height),
                                          thwart_outer_wire.OrderedVertexes[0].Point
                                          )
    thwart_edges = thwart_outer_wire.Edges + [thwart_top_edge, thwart_center_edge]

    thwart_wire = Part.Wire(Part.Shape(thwart_edges).Edges)
    thwart_face = Part.makeFace([thwart_wire])
    #Part.show(thwart_face, "thwart_face")

    rib_face = rib_face.fuse(thwart_face)
    rib_face = rib_face.cleaned()
    rib_face.removeInternalWires(1)
    rib_face = rib_face.removeSplitter()
    #Part.show(rib_face, "rib_face")

    for stringer in self.stringers:
      for solid in stringer.Solids:
        rib_face = rib_face.cut(solid)
    if self.keelson:
      rib_face = rib_face.cut(self.keelson)
    for stem in self.stem:
      rib_face = rib_face.cut(self.stem)
    for stern in self.stern:
      rib_face = rib_face.cut(self.stern)

    rib_face.translate(-App.Vector(0, 1, 0) * rib_thickness / 2)
    rib_solid = rib_face.extrude(App.Vector(0, 1, 0) * rib_thickness)

    self.ribs[rib_position] = rib_solid

  def draw_rib_sof(self, doc, rib_position: float, rib_index: int, rib_wire: Part.Wire):
    dimensions = doc.getObjectsByLabel("dimensions")[0]
    rib_thickness = dimensions.get("rib_thickness").Value
    rib_depth = dimensions.get("rib_depth").Value
    rib_thwart_depth = dimensions.get("rib_thwart_depth").Value
    brace_width = dimensions.get("brace_width").Value
    brace_width_narrow = dimensions.get("brace_width_narrow").Value
    rib_chamfer_radius = dimensions.get("rib_chamfer_radius")
    rib_chamfer_radius_narrow = dimensions.get("rib_chamfer_radius_narrow")
    rib_outside_relief = dimensions.get("rib_outside_relief")
    thwart_height = dimensions.get("thwart_height").Value
    low_thwart_height = dimensions.get("low_thwart_height").Value
    deck_width = dimensions.get("deck_width")
    deck_height = dimensions.get("deck_height")
    rib_type = dimensions.get(f"rib_type_{rib_index}")

    if rib_type == "thwart_narrow":
      brace_width = brace_width_narrow
      rib_chamfer_radius = rib_chamfer_radius_narrow

    if rib_wire.Length < 1:
      return
    if rib_type == "skip":
      return

    # Get shapes of intersections between stringer and rib.
    plane = Part.Plane(App.Vector(0, int(rib_position), 0), App.Vector(0, 1, 0))
    stringers_intersection = []
    for stringer_deep in sorted(self.stringers_deep, key=lambda stringer : stringer.distToShape(Part.Vertex(0, 0, 0)), reverse=True):
      stringers_intersection.append(stringer_deep.common(plane))
      #Part.show(stringers_intersection[-1], "stringer_intersection")

    # Work out which parts of rib outline are between stringers.
    rib_wire_vertexes = sorted(rib_wire.copy().OrderedVertexes, key=lambda vertex : vertex.distToShape(Part.Vertex(0, 0, 0)), reverse=True)
    top_outer = rib_wire_vertexes[0]
    bottom_center = rib_wire_vertexes[-1]
    deck = Part.makeLine(top_outer.Point, top_outer.Point - App.Vector(deck_width.Value, 0.0, 0.0))

    rib_wire_with_deck = rib_wire.copy()
    rib_wire_with_deck.add(deck)
    rib_parts = rib_wire_with_deck.common(stringers_intersection)

    # Calculate a new rib outline, curving parts between stringers away from hull's skin.
    previous = bottom_center.Point
    new_rib_parts = []
    # Iterate parts we want rib edge to go through, from lowest part to highest.
    for rib_part in sorted(rib_parts.Edges, key = lambda edge: edge.BoundBox.ZMin):
      #Part.show(rib_part, "rib_part")

      # Sort Vertexes from lowest to highest.
      vertexes = sorted(rib_part.Vertexes, key=lambda vertex: vertex.Point.z)

      if abs(vertexes[0].Point.z - vertexes[-1].Point.z) < 1e-3:
        # Line section is horizontal. Must be part of the deck so we are done.
        break

      if previous is None:
        # First time through.
        previous = vertexes[-1].Point
        new_rib_parts.append(rib_part)
        continue

      vertex = vertexes[0].Point
      if previous == vertex:
        # Sections are separate edges.
        previous = vertexes[-1].Point
        new_rib_parts.append(rib_part)
        continue

      # Curve ribs away from skin between stringers.
      diff = (vertex - previous)
      diff.normalize()
      diff *= rib_outside_relief
      cross = (diff / 2).cross(App.Vector(0, 1, 0))
      new = (previous + vertex) / 2 + cross
      arc = Part.Arc(previous, new, vertex).toShape()
      previous = vertexes[-1].Point
      new_rib_parts.append(arc)
      new_rib_parts.append(rib_part)
    outer_rib_wire = Part.Wire(new_rib_parts)
    #Part.show(outer_rib_wire, "outer_rib_wire")

    inner_rib_wire = rib_wire.makeOffset2D(-rib_depth, openResult = True, fill = False)

    boundary = Part.makeBox(inner_rib_wire.BoundBox.XMax, inner_rib_wire.BoundBox.YLength, inner_rib_wire.BoundBox.ZLength,
                            App.Vector(0, inner_rib_wire.BoundBox.YMin, inner_rib_wire.BoundBox.ZMin))
    section = inner_rib_wire.common(boundary)
    inner_rib_wire = section.Wires[0]
    #Part.show(inner_rib_wire.copy(), "inner_rib_wire")

    outer_ends = get_wire_ends(outer_rib_wire)
    inner_ends = get_wire_ends(inner_rib_wire)

    bottom = Part.makeLine(outer_ends[-1], inner_ends[-1])
    top = Part.makeLine(inner_ends[0], outer_ends[0])
    inner_rib_wire.add(top)
    inner_rib_wire.add(bottom)
    rib_wire = Part.Wire([inner_rib_wire, outer_rib_wire], closed = True)
    #Part.show(rib_wire, "rib_wire")
    rib_face = Part.Face(rib_wire)


    if abs(rib_wire.BoundBox.XMax) > rib_depth * 2:
      # Big enough to fit thwarts in.
      if rib_type == "open":
        thwart_height = low_thwart_height

      rib_intersection_height = Part.makeLine(
          App.Vector(deck_width.Value, float(rib_position), thwart_height),
          App.Vector(0.0, float(rib_position), thwart_height)
      )
      rib_intersection_bottom = Part.makeLine(
          App.Vector(brace_width / 2, float(rib_position), thwart_height),
          App.Vector(brace_width / 2, float(rib_position), 0.0)
      )

      thwart_edge = None
      brace_edge = None

      best_thwart_edge_point = None
      for edge in rib_wire.Edges:
        common = DraftGeomUtils.findIntersection(rib_intersection_height, edge)
        point_center = App.Vector(0.0, float(rib_position), thwart_height)
        for point in common:
          if point != point_center and (best_thwart_edge_point is None or point.x < best_thwart_edge_point.x):
            # This is the point on the inside of the rib, not the outside, nearest the hull's outer skin.
            best_thwart_edge_point = point
            thwart_edge = Part.makeLine(point, point_center)

        common = DraftGeomUtils.findIntersection(rib_intersection_bottom, edge)
        point_center = App.Vector(brace_width / 2, float(rib_position), thwart_height)
        for point in common:
          if point != point_center:
            brace_edge = Part.makeLine(point, point_center)

      if thwart_edge:
        thwart_face = thwart_edge.extrude(App.Vector(0, 0, 1) * -rib_thwart_depth)
        rib_face = rib_face.fuse(thwart_face)

      if brace_edge:
        brace_face = brace_edge.extrude(App.Vector(1, 0, 0) * -brace_width / 2)
        rib_face = rib_face.fuse(brace_face)

      rib_face = DraftGeomUtils.concatenate(rib_face)
      if rib_type in ("thwart", "thwart_narrow"):
        rib_face = self.chamfer_rib_hole(rib_face, rib_chamfer_radius, deck_width)
    else:
      # Too small to do offset. Just make a solid rib.
      xmin = min(outer_rib_wire.OrderedVertexes[0].X, outer_rib_wire.OrderedVertexes[-1].X)
      zmin = min(outer_rib_wire.OrderedVertexes[0].Z, outer_rib_wire.OrderedVertexes[-1].Z)
      xmax = max(outer_rib_wire.OrderedVertexes[0].X, outer_rib_wire.OrderedVertexes[-1].X)
      zmax = max(outer_rib_wire.OrderedVertexes[0].Z, outer_rib_wire.OrderedVertexes[-1].Z)
      y = outer_rib_wire.OrderedVertexes[0].Y

      edge_top = Part.makeLine((xmax, y, zmax), (0, y, zmax))
      edge_center = Part.makeLine((0, y, zmax), (0, y, zmin))
      wire = Part.Wire([outer_rib_wire, edge_top, edge_center])
      rib_face = Part.Face(wire)

    rib_face = rib_face.common(self.hull)
    rib_face.translate(-App.Vector(0, 1, 0) * rib_thickness / 2)

    #to_cut = [solid for stringer in self.stringers_deep for solid in stringer.Solids]
    #rib_face = rib_face.cut(to_cut)
    # Interestingly it's quicker to cut these out one at a time rather than provide a list in a  single cut.
    for stringer_deep in self.stringers_deep:
      for solid in stringer_deep.Solids:
        rib_face = rib_face.cut(solid)
    if self.keelson:
      rib_face = rib_face.cut(self.keelson)
    for stem in self.stem:
      rib_face = rib_face.cut(self.stem)
    for stern in self.stern:
      rib_face = rib_face.cut(self.stern)

    rib_solid = rib_face.extrude(App.Vector(0, 1, 0) * rib_thickness)

    self.ribs[rib_position] = rib_solid

  def chamfer_rib_hole(self, rib_face, rib_chamfer_radius, deck_width):
    inner_wire = sorted(rib_face.Wires, key=lambda value: value.Length)[0]
    if inner_wire.BoundBox.XLength < 2 * rib_chamfer_radius or inner_wire.BoundBox.ZLength < 2 * rib_chamfer_radius:
      # Holes too small to care about. Remove them.
      rib_face.removeInternalWires((4 * rib_chamfer_radius) ** 2)
      return rib_face

    # Remove too short edges.
    inner_wire = Part.Wire(list(filter(lambda edge: edge.Length > 1e-4, inner_wire.Edges)))

    outer_wire = sorted(rib_face.Wires, key=lambda value: value.Length)[-1]
    outer_face = Part.Face(outer_wire)

    try:
      offset = inner_wire.makeOffset2D(-rib_chamfer_radius, openResult = False, fill = False)
    except:
      inner_wire.reverse()
      try:
        offset = inner_wire.makeOffset2D(-rib_chamfer_radius, openResult = False, fill = False)
      except:
        print("WARN: Failed to fillet rib. Try reducing 'rib_chamfer_radius' value. A")
        return rib_face

    previous = offset.Edges[-1]
    for offset_edge in offset.Edges:
      if offset_edge.Vertexes[0].Point == previous.Vertexes[0].Point:
        common = offset_edge.Vertexes[0].Point
        other = (offset_edge.Vertexes[-1].Point, previous.Vertexes[-1].Point)
      elif offset_edge.Vertexes[0].Point == previous.Vertexes[-1].Point:
        common = offset_edge.Vertexes[0].Point
        other = (offset_edge.Vertexes[-1].Point, previous.Vertexes[0].Point)
      elif offset_edge.Vertexes[-1].Point == previous.Vertexes[0].Point:
        common = offset_edge.Vertexes[-1].Point
        other = (offset_edge.Vertexes[0].Point, previous.Vertexes[-1].Point)
      elif offset_edge.Vertexes[-1].Point == previous.Vertexes[-1].Point:
        common = offset_edge.Vertexes[-1].Point
        other = (offset_edge.Vertexes[0].Point, previous.Vertexes[0].Point)
      else:
        print("WARN: Failed to fillet rib. Try reducing 'rib_chamfer_radius' value. B")
        continue
      previous = offset_edge

      v1 = (common - other[0])
      v1.normalize()
      v2 = (common - other[1])
      v2.normalize()

      angle = math.acos(v1.dot(v2))
      #print(round(math.degrees(angle)))
      if angle > 3 * math.pi / 4:
        continue

      arc = Part.makeCircle(rib_chamfer_radius, common, App.Vector(0, 1, 0))
      arc_end_angles = []
      arc_end_vertex = []
      arc_end_edge = []
      for edge in inner_wire.Edges:
        dist, vec, infos = edge.distToShape(arc)
        if dist < 0.0001:
          angle = infos[0][5]
          arc_end_angles.append(math.degrees(angle))
          arc_end_vertex.append(vec[0][0])
          arc_end_edge.append(edge)

      if len(arc_end_angles) != 2:
        print(f"WARN: Unexpected number of intersections ({len(arc_end_angles)}) between arc and outline wire.")
        return rib_face

      angle_diff = arc_end_angles[0] - arc_end_angles[1]
      if angle_diff < 0:
        angle_diff += 360
      if angle_diff < 180:
        arc = Part.makeCircle(rib_chamfer_radius, common, App.Vector(0, 1, 0), arc_end_angles[1], arc_end_angles[0])
      else:
        arc = Part.makeCircle(rib_chamfer_radius, common, App.Vector(0, 1, 0), arc_end_angles[0], arc_end_angles[1])
      arc_offset = arc.makeOffset2D(-deck_width, openResult = True, fill = True)
      arc_offset = arc_offset.common(outer_face)  # Can probably do this once for all 3 arcs.
      #Part.show(arc_offset, "arc_offset")

      rib_face = rib_face.fuse(arc_offset)
    return rib_face

  def draw_daggerboard_case(self):
    dimensions = doc.getObjectsByLabel("dimensions")[0]
    thwart_height = dimensions.get("thwart_height")
    rib_thickness = dimensions.get("rib_thickness")
    rib_thickness = dimensions.get("rib_thickness")
    stem_depth = dimensions.get("stem_depth")
    dagger_board = doc.getObjectsByLabel('dagger_board')[0]

    case = Part.makeBox(rib_thickness * 3, dagger_board.Shape.BoundBox.YLength, thwart_height + stem_depth,
                        App.Vector(-rib_thickness * 1.5, dagger_board.Shape.BoundBox.YMin, -stem_depth), App.Vector(0, 0, 1))

    group_component = create_group(doc, f"dagger_board_case")
    self.group.addObjects([group_component])
    group_component.addObjects([ Part.show(case) ])
    self.dagger_board_case = case
    self.components_flat["dagger_board_case"] = case

  def draw_stem(self):
    dimensions = doc.getObjectsByLabel("dimensions")[0]
    deck_length = dimensions.get("deck_length")
    stem_height = dimensions.get("stem_height")
    dagger_board = doc.getObjectsByLabel('dagger_board')[0]

    print("Calculating stem")

    min_y = -deck_length.Value / 2
    max_y = dagger_board.Shape.BoundBox.YMin

    group_component = create_group(doc, f"stem")
    self.group.addObjects([group_component])

    parts_3d = self.draw_stem_stern(min_y, max_y, stem_height, figure_head=True)
    for part_3d in parts_3d:
      part_3d = self.trim_transom(part_3d)
      group_component.addObjects([ Part.show(part_3d) ])

    self.stem = parts_3d
    for index, part_3d in enumerate(parts_3d):
      self.components_flat[f"stem_{index}"] = part_3d

  def draw_stern(self):
    dimensions = doc.getObjectsByLabel("dimensions")[0]
    deck_length = dimensions.get("deck_length")
    stern_height = dimensions.get("stern_height")
    dagger_board = doc.getObjectsByLabel('dagger_board')[0]

    print("Calculating stern")

    min_y = dagger_board.Shape.BoundBox.YMax
    max_y = deck_length.Value / 2

    group_component = create_group(doc, f"stern")
    self.group.addObjects([group_component])

    parts_3d = self.draw_stem_stern(min_y, max_y, stern_height, skeg=True)
    for part_3d in parts_3d:
      part_3d = self.trim_transom(part_3d)
      group_component.addObjects([ Part.show(part_3d) ])

    self.stern = parts_3d
    for index, part_3d in enumerate(parts_3d):
      self.components_flat[f"stern_{index}"] = part_3d

  def draw_stem_stern(self, min_y, max_y, max_z, skeg=False, figure_head=False):
    profile_keel = doc.getObjectsByLabel('profile_keel')[0]
    dimensions = doc.getObjectsByLabel("dimensions")[0]
    stem_depth = dimensions.get("stem_depth")
    stem_height = dimensions.get("stem_height")
    rib_thickness = dimensions.get("rib_thickness")
    hull_type = dimensions.get("hull_type")
    plank_thickness = dimensions.get("plank_thickness")
    transom_angle = dimensions.get("transom_angle")

    output_shapes = []

    hull_max_z = self.hull.BoundBox.ZMax
    min_z = 0

    box = Part.makeBox(2, max_y - min_y, hull_max_z, App.Vector(-1, min_y, min_z), App.Vector(0, 0, 1))
    section = box.common(profile_keel.Shape)
    keel_wire = section.Wires[0]

    for x_pos, inner_offset, outer_offset in (
        (0,                    stem_height,            -stem_depth),
        (-rib_thickness.Value, -plank_thickness.Value, -stem_depth),
        (rib_thickness.Value,  -plank_thickness.Value, -stem_depth)):
      outer_wire = keel_wire.copy().translate(App.Vector(1, 0, 0) * (x_pos - (rib_thickness.Value / 2)))
      outer_wire = self.offset_direction(outer_wire, outer_offset)

      inner_wire = keel_wire.copy().translate(App.Vector(1, 0, 0) * (x_pos - (rib_thickness.Value / 2)))
      inner_wire = self.offset_direction(inner_wire, inner_offset)

      if skeg:
        first = outer_wire.OrderedVertexes[0].Point
        last = outer_wire.OrderedVertexes[-1].Point
        start = first if first.y < last.y else last
        end = first if first.y > last.y else last
        y = math.tan(math.radians(transom_angle)) * (end.z + stem_depth.Value)
        corner = App.Vector(end.x, end.y - y, -stem_depth)
        end = App.Vector(end.x, end.y, max_z)
        skeg_edges = [
            Part.makeLine(corner, start),
            Part.makeLine(end, corner),
            ]
        outer_wire = Part.Wire(Part.sortEdges(skeg_edges)[0])

      d1 = outer_wire.OrderedVertexes[0].Point.distanceToPoint(inner_wire.OrderedVertexes[0].Point)
      d2 = outer_wire.OrderedVertexes[0].Point.distanceToPoint(inner_wire.OrderedVertexes[-1].Point)
      if (d1 < d2):
        print("reversing outer_wire")
        outer_wire.reverse()

      joined_wire = join_wires([
        outer_wire,
        Part.makeLine(outer_wire.OrderedVertexes[-1].Point, inner_wire.OrderedVertexes[0].Point),
        inner_wire,
        Part.makeLine(inner_wire.OrderedVertexes[-1].Point, outer_wire.OrderedVertexes[0].Point),
        ])
      #Part.show(joined_wire, "joined_wire")
      face = Part.Face(joined_wire)
      if figure_head:
        face = self.add_figgurehead(face, outer_wire, inner_wire)
      #Part.show(face, "face")

      part_3d = face.extrude(App.Vector(1, 0, 0) * rib_thickness)
      output_shapes.append(part_3d)

    index = 0
    while True:
      rib_pos_label = f"rib_positions_{index}"
      rib_type_label = f"rib_type_{index}"
      try:
        rib_position = dimensions.get(rib_pos_label)
        rib_type = dimensions.get(rib_type_label)
      except ValueError:
        break

      index += 1

      if rib_type == "skip":
        continue

      if rib_position < min_y or rib_position > max_y:
        continue

      intersect = Part.makeLine(App.Vector(0, rib_position, self.hull.BoundBox.ZMin), App.Vector(0, rib_position, self.hull.BoundBox.ZMax))
      high_point = intersect.common(output_shapes[0]).BoundBox.ZMax

      slot = Part.makeBox(rib_thickness * 2, rib_thickness.Value + 0.2, stem_height,
                          App.Vector(-rib_thickness, rib_position - rib_thickness.Value / 2 - 0.1,
                                     high_point - stem_height.Value / 2), App.Vector(0, 0, 1))
      output_shapes[0] = output_shapes[0].cut(slot)

    return output_shapes

  @classmethod
  def offset_direction(cls, wire: Part.Wire, distance: float) -> Part.Wire:
    """
    Args: distance: Negative results in wire being moved downwards. Positive = upwards.
    """
    min_z = wire.BoundBox.ZMin
    wire_copy = wire.copy().makeOffset2D(abs(distance), openResult = True)
    min_z_copy = wire_copy.BoundBox.ZMin
    if (distance < 0) == (min_z_copy < min_z):
      return wire_copy

    wire_copy =  wire.copy().makeOffset2D(-abs(distance), openResult = True)
    return wire_copy

  def add_figgurehead(self, face, outer_wire, inner_wire) -> Part.Face:
    if not self.figurehead:
      dimensions = doc.getObjectsByLabel("dimensions")[0]
      stem_depth = dimensions.get("stem_depth")
      stem_height = dimensions.get("stem_height")

      first = inner_wire.OrderedVertexes[0]
      last = outer_wire.OrderedVertexes[-1]
      center = first if first.Z > last.Z else last
      circle = Part.makeCircle(stem_height + stem_depth, center.Point, App.Vector(-1, 0, 0))
      self.figurehead = Part.makeFace([circle])

    face_tmp = self.figurehead.copy().translate(App.Vector(1, 0, 0) * (outer_wire.Vertexes[0].X - self.figurehead.BoundBox.XMin))
    face_tmp = face_tmp.cut(face)
    face_tmp = face_tmp.fuse(face)
    face = face_tmp
    face = face.removeSplitter()
    return face

  def draw_keelson(self):
    #profile_keel = doc.getObjectsByLabel('profile_keel')[0]
    dimensions = doc.getObjectsByLabel("dimensions")[0]
    do_keelson = dimensions.get("keelson")
    prow_height = dimensions.get("prow_height")
    keelson_length = dimensions.get("keelson_length")
    keelson_width = dimensions.get("keelson_width")
    keelson_depth = dimensions.get("keelson_depth")
    accurate_stringers = dimensions.get("accurate_stringers")

    if int(do_keelson) <= 0:
      return

    print("Calculating keelson")

    part_3d = Part.makeBox(keelson_width, keelson_length, keelson_depth, App.Vector(-keelson_width / 2, -keelson_length / 2, 0), App.Vector(0, 0, 1))
    part_3d = part_3d.common(self.hull)

    group_component = create_group(doc, f"keelson")
    self.group.addObjects([group_component])
    group_component.addObjects([ Part.show(part_3d) ])
    self.keelson = part_3d
    self.components_bulk["keelson"] = part_3d

  def draw_rudder(self):
    dimensions = doc.getObjectsByLabel("dimensions")[0]
    deck_length = dimensions.get("deck_length")
    stern_height = dimensions.get("stern_height")
    stem_depth = dimensions.get("stem_depth")
    transom_angle = dimensions.get("transom_angle")
    rudder_width = dimensions.get("rudder_width")
    rib_thickness = dimensions.get("rib_thickness")
    rudder_post_depth = 15
    rudder_pintel_thickness = 2
    extra_blade_space = 0.05 * rudder_width.Value / 2

    print("Calculating rudder")

    root_y = deck_length.Value / 2 + stem_depth.Value + rudder_pintel_thickness
    root_point = App.Vector(0, root_y, stern_height)

    bottom_inner_y = root_y - math.tan(math.radians(transom_angle)) * (root_point.z + stem_depth.Value)
    bottom_inner_point = App.Vector(0, bottom_inner_y, -stem_depth)

    top_inner_y = root_y + math.tan(math.radians(transom_angle)) * rudder_post_depth
    top_inner_point = App.Vector(0, top_inner_y, stern_height.Value + rudder_post_depth)

    top_outer_y = top_inner_y + rudder_post_depth + extra_blade_space
    top_outer_point = App.Vector(0, top_outer_y, stern_height.Value + rudder_post_depth)

    bottom_outer_y = top_outer_y
    bottom_outer_point = App.Vector(0, bottom_outer_y, -stem_depth)

    bottom_mid_y = (bottom_inner_y + bottom_outer_y) / 2
    bottom_mid_point = App.Vector(0, bottom_mid_y, -stem_depth)

    edge_inner = Part.makeLine(top_inner_point, bottom_inner_point)
    edge_bottom = Part.makeLine(bottom_inner_point, bottom_outer_point)
    edge_outer = Part.makeLine(bottom_outer_point, top_outer_point)
    edge_top = Part.makeLine(top_outer_point, top_inner_point)

    outer_case_line = Part.Wire([ edge_inner, edge_bottom, edge_outer, edge_top ])

    rudder_space = rudder_width.Value / 2 + extra_blade_space

    pivot_point = App.Vector(0, bottom_outer_y - rudder_space, rudder_space - stem_depth.Value)
    pivot = Part.makeCircle(0.5, pivot_point, App.Vector(1, 0, 0))
    pivot = Part.Wire(pivot.Edges)

    inner_case_blade_slot_bottom = App.Vector(0, pivot_point.y - rudder_space, -stem_depth)
    inner_case_blade_arc_inner = App.Vector(0, pivot_point.y - rudder_space, pivot_point.z)
    inner_case_blade_arc_top = App.Vector(0, pivot_point.y, pivot_point.z + rudder_space)
    outer_case_bottom_outer_point = App.Vector(0, top_outer_y, pivot_point.z + rudder_space)

    inner_case_edge_bottom = Part.makeLine(
        bottom_inner_point,
        inner_case_blade_slot_bottom
        )

    inner_case_edge_inner = Part.makeLine(
        inner_case_blade_slot_bottom,
        inner_case_blade_arc_inner
        )

    inner_case_edge_arc = Part.Arc(
        inner_case_blade_arc_inner,
        inner_case_blade_arc_top,
        App.Vector(0, pivot_point.y + rudder_space, pivot_point.z)
        ).toShape()
    inner_case_edge_arc = inner_case_edge_arc.split(math.pi / 2).Edges[0]

    inner_case_edge_arc_to_outer = Part.makeLine(
        inner_case_blade_arc_top,
        outer_case_bottom_outer_point
        )

    inner_case_edge_outer = Part.makeLine(
        outer_case_bottom_outer_point,
        top_outer_point
        )

    inner_case_line = Part.Wire([
      edge_inner,
      inner_case_edge_bottom,
      inner_case_edge_inner,
      inner_case_edge_arc,
      inner_case_edge_arc_to_outer,
      inner_case_edge_outer,
      edge_top
      ])

    group = create_group(doc, f"rudder")
    self.group.addObjects([group])

    self.wire_to_solid("rudder_outer_port", group, outer_case_line.Wires + pivot.Wires, rib_thickness, App.Vector(1, 0, 0), App.Vector(1, 0, 0) * rib_thickness)
    self.wire_to_solid("rudder_outer_starboard", group, outer_case_line.Wires + pivot.Wires, rib_thickness, App.Vector(1, 0, 0), App.Vector(1, 0, 0) * -rib_thickness)
    self.wire_to_solid("rudder_inner", group, inner_case_line.Wires, rib_thickness, App.Vector(1, 0, 0))

  def wire_to_solid(self, name, group, wires, thickness, direction, translate=App.Vector(0, 0, 0)):
    for wire in wires[:1]:
      wire.reverse()
    face = Part.Face(wires)
    face.translate(translate)
    part = face.extrude(direction * thickness)
    part.translate(direction * -thickness / 2)

    solid = Part.show(part, name)
    group.addObjects([ solid ])
    self.components_flat[name] = part

  def mirror_sides(self):
    for rib_position, rib in self.ribs.items():
      print(f"Mirroring rib {rib_position}")
      rib_mirrored = rib.copy().mirror(App.Vector(0, 0, 0), App.Vector(1, 0, 0))
      rib = rib.fuse(rib_mirrored)
      rib = rib.removeSplitter()

      self.ribs[rib_position] = rib
      name = f"rib_{rib_position}"
      self.rib_group.addObjects([Part.show(rib, name)])
      self.components_flat[name] = rib

    for stringer in self.stringers:
      print("Mirroring stringer")
      stringer_mirrored = stringer.copy().mirror(App.Vector(0, 0, 0), App.Vector(1, 0, 0))
      #stringer = stringer.fuse(stringer_mirrored)
      name = f"stringer_{round(stringer.BoundBox.ZMin)}"
      name_port = f"{name}_port"
      name_starboard = f"{name}_starboard"
      if name_port in self.components_bulk:
        name_port = name_port + "_2"
        name_starboard = name_starboard + "_2"
      self.stringers_group.addObjects([
        Part.show(stringer, name_port),
        Part.show(stringer_mirrored, name_starboard)])
      self.components_bulk[name_port] = stringer
      self.components_bulk[name_starboard] = stringer_mirrored

    for index, plank in enumerate(self.planks):
      plank_mirrored = plank.mirror(App.Vector(0, 0, 0), App.Vector(1, 0, 0))
      name = f"plank_{index}"
      name_port = f"{name}_port"
      name_starboard = f"{name}_starboard"

      plank_mirrored_display = Part.show(plank_mirrored, name_starboard)
      self.solid_planks_group.addObject(plank_mirrored_display)

    for name, plank in self.flat_planks.items():
      #plank_nominal, plank_overlap = plank
      plank_overlap = plank

      #plank_nominal_mirrored = plank_nominal.mirror(App.Vector(0, 0, 0), App.Vector(1, 0, 0))
      plank_overlap_mirrored = plank_overlap.mirror(App.Vector(0, 0, 0), App.Vector(1, 0, 0))

      name_port = f"{name}_port"
      name_starboard = f"{name}_starboard"

      #self.components_flat[name_port] = (plank_nominal, plank_overlap)
      #self.components_flat[name_starboard] = (plank_nominal_mirrored, plank_overlap_mirrored)
      self.components_flat[name_port] = plank_overlap
      self.components_flat[name_starboard] = plank_overlap_mirrored

  @classmethod
  def diagonal_normal_at(cls, diagonal):
    for diagonal_edge in diagonal.Edges:
      plane = diagonal_edge.Curve.toShape().findPlane()
      if plane:
        return plane.Axis
    return None

  def draw_deck(self):
    dimensions = doc.getObjectsByLabel("dimensions")[0]
    thwart_height = dimensions.get("thwart_height")
    stringer_depth = dimensions.get("stringer_depth")
    deck_thickness = dimensions.get("deck_thickness")
    deck_width = dimensions.get("deck_width")
    deck_gap = dimensions.get("deck_gap")
    rib_thickness = dimensions.get("rib_thickness")

    deck_section_indexes = [
        (0, 2),
        (3, 4),
        (6, 8)
        ]
    index = 0
    while True:
      deck_label = f"deck_{index}"
      try:
        deck_section = dimensions.get(deck_label)
      except ValueError:
        break
      deck_section_index = (int(rib) for rib in deck_section.split(","))
      deck_section_indexes.append(deck_section_index)
      index += 1

    rib_positions = []
    index = 0
    while True:
      rib_pos_label = f"rib_positions_{index}"
      try:
        rib_position = dimensions.get(rib_pos_label)
      except ValueError:
        break
      rib_positions.append(rib_position)
      index += 1

    plane = Part.Plane(App.Vector(0, 0, thwart_height), App.Vector(0, 0, 1))
    deck_plan = self.hull.common(plane)
    outline = clean_wire(deck_plan.Wires[0])

    offset = outline.makeOffset2D(-deck_gap, openResult = False)
    offset.fix(0.1, 0, 1)
    #Part.show(offset, "offset")

    face = Part.Face(offset)
    #Part.show(face, "face")

    full_deck = face.extrude(App.Vector(0, 0, deck_thickness))
    #Part.show(full_deck, "full_deck")

    group_component = create_group(doc, f"deck")
    self.group.addObjects([group_component])

    for index_start, index_end in deck_section_indexes:
      part_name = f"deck_section_{index_start}_{index_end}"
      print("Drawing", part_name)
      mask_len = rib_positions[index_end] - rib_positions[index_start] + rib_thickness.Value
      mask = Part.makeBox(deck_width, mask_len, deck_thickness * 2, App.Vector(-deck_width / 2, rib_positions[index_start] - rib_thickness.Value / 2, thwart_height))
      deck_part = mask.common(full_deck.copy())

      for key, value in self.components_flat.items():
        if key.split("_")[0] in ["rib", "stem", "stern"]:
          deck_part = deck_part.cut(value)

      deck_part = deck_part.common(self.hull)
      deck_part = self.trim_transom(deck_part)

      group_component.addObjects([ Part.show(deck_part, part_name) ])
      self.components_flat[part_name] = deck_part

  def trim_transom(self, to_trim):
    """ Mask out components overhanging transom """
    dimensions = doc.getObjectsByLabel("dimensions")[0]
    rib_thickness = dimensions.get("rib_thickness")
    stern_height = dimensions.get("stern_height")
    deck_width = dimensions.get("deck_width")
    deck_length = dimensions.get("deck_length")
    transom_angle = dimensions.get("transom_angle")
    transom_overlap = dimensions.get("transom_overlap")

    if transom_overlap <= 0:
      return to_trim

    transom_mask = Part.makeBox(deck_width, transom_overlap * 3, stern_height * 3,
                                App.Vector(-deck_width / 2, deck_length / 2 - rib_thickness, -stern_height),
                                App.Vector(0, 0, 1))
    transom_mask = transom_mask.rotate(App.Vector(0, deck_length / 2, stern_height),
                                       App.Vector(1, 0, 0),
                                       -transom_angle)

    return to_trim.cut(transom_mask)


  def draw_transom(self):
    dimensions = doc.getObjectsByLabel("dimensions")[0]
    rib_thickness = dimensions.get("rib_thickness")
    stern_height = dimensions.get("stern_height")
    deck_length = dimensions.get("deck_length")
    transom_angle = dimensions.get("transom_angle")
    transom_overlap = dimensions.get("transom_overlap")

    if transom_overlap <= 0:
      return

    plane = Part.Plane(
        App.Vector(0, 0, 0),
        App.Vector(0, 1, 0))
    plane.rotate(
        App.Placement(
          App.Vector(0, 0, stern_height),
          App.Vector(1, 0, 0),
          -transom_angle
          )
        )
    plane.translate(App.Vector(0, 1, 0) * ((deck_length / 2) - rib_thickness))

    transom_face = self.hull.common(plane)
    transom_face.rotate(
        App.Vector(0, 0, 0),
        App.Vector(1, 0, 0),
        transom_angle
        )
    transom = transom_face.extrude(App.Vector(0, 1, 0) * rib_thickness.Value)
    transom.rotate(
        App.Vector(0, 0, 0),
        App.Vector(1, 0, 0),
        -transom_angle
        )

    self.rib_group.addObjects([ Part.show(transom, "transom") ])
    self.components_flat["transom"] = transom


class Mass:
  centers = []
  def __init__(self, doc, components: Components):
    self.doc = doc
    self.components = components

    dimensions = doc.getObjectsByLabel("dimensions")[0]
    plywood_density = dimensions.get("plywood_density")
    pine_density = dimensions.get("pine_density")

    flat_volume = self.get_volume(components.components_flat, "flat", plywood_density)
    bulk_volume = self.get_volume(components.components_bulk, "bulk", pine_density)

    flat_volume_m3 = round(flat_volume, 5)
    bulk_volume_m3 = round(bulk_volume, 5)
    total_volume_m3 = flat_volume_m3 + bulk_volume_m3
    flat_weight_kg = flat_volume_m3 * plywood_density
    bulk_weight_kg = bulk_volume_m3 * pine_density
    total_weight_kg = flat_weight_kg + bulk_weight_kg
    print(
        f"pine:    {bulk_volume_m3:4.5f}m³ {bulk_weight_kg:4.2f}kg")
    print(
        f"plywood: {flat_volume_m3:4.5f}m³ {flat_weight_kg:4.2f}kg")
    print("---------------------------")
    print(
        f"total:   {total_volume_m3:4.5f}m³ {total_weight_kg:4.2f}kg")
    print("---------------------------")

  def get_volume(self, parts, type_, density):
    total_volume = 0
    for label, component in parts.items():
      volume = abs(component.Volume / 1e9)
      print(f"{label:<25}:{volume:4.5f}m³   {volume * density:4.2f}kg   {type_}")
      total_volume += volume
    return total_volume


class Layout:
  bodies = {}
  faces = []

  def __init__(self, doc, components: Components):
    self.doc = doc
    self.components = components
    self.cutouts = create_group(doc, "cutouts", type_ = 'App::Part')
    self.cutouts.Visibility = False
    self.scratch = create_group(self.doc, "scratch_plans")
    self.scratch.Visibility = False
    self.plans = create_group(self.doc, "plans")

    self.project_parts()
    self.draw_plans()
    self.export_dxf()

  def project_parts(self):
    dimensions = doc.getObjectsByLabel("dimensions")[0]
    transom_angle = dimensions.get("transom_angle")
    x_pos_offset = 1000
    y_pos_offset = -2000
    y_pos_mod = 0
    for label, component in self.components.components_flat.items():
      label = label.replace("-", "M")
      print(label, type(component))
      if isinstance(component, Part.Feature):
        component = component.Shape.copy()
      if "rib" in label:
        direction = App.Vector(1, 0, 0)
        x_pos = component.BoundBox.XLength / 2 + x_pos_offset
        y_pos = y_pos_offset
        y_pos_mod += component.BoundBox.ZLength + 50
        z_pos = -component.BoundBox.YMin
      elif label.split("_")[0] in ["stem", "stern"]:
        direction = App.Vector(0, 1, 0)
        x_pos = x_pos_offset
        y_pos = -component.BoundBox.YMax + y_pos_offset
        y_pos_mod += component.BoundBox.YLength + 50
        z_pos = -component.BoundBox.XMin
      elif "deck" in label:
        direction = App.Vector(0, 0, 1)
        x_pos = x_pos_offset + component.BoundBox.YMax
        y_pos = y_pos_offset
        y_pos_mod += component.BoundBox.XLength + 50
        z_pos = -component.BoundBox.XMin
      elif "plank_bow" in label or "plank_stern" in label:
        direction = App.Vector(0, 0, 1)
        x_pos = x_pos_offset + component.BoundBox.YMax
        y_pos = y_pos_offset
        y_pos_mod += component.BoundBox.XLength + 50
        z_pos = -component.BoundBox.XMin
      elif "transom" == label:
        direction = App.Vector(1, 0, 0)
        component = component.copy()
        component.rotate(
            App.Vector(0, 0, 0),
            App.Vector(1, 0, 0),
            transom_angle
            )
        x_pos = component.BoundBox.XLength / 2 + x_pos_offset
        y_pos = y_pos_offset
        y_pos_mod += component.BoundBox.ZLength + 50
        z_pos = -component.BoundBox.YMin
      elif "rudder" in label:
        direction = App.Vector(0, 1, 0)
        x_pos = x_pos_offset
        y_pos = -component.BoundBox.YMax + y_pos_offset
        y_pos_mod += component.BoundBox.YLength + 50
        z_pos = -component.BoundBox.XMin

      body = doc.addObject('PartDesign::Body', f"cutout_{label}")
      self.cutouts.addObject(body)
      feature = App.ActiveDocument.addObject("Part::Feature", f"cutout_feature_{label}")
      feature.Label = f"cutout_feature_{label}"
      self.cutouts.addObject(feature)
      feature.Shape = component
      body.BaseFeature = feature
      feature.ViewObject.Visibility = False

      y_pos += y_pos_mod
      body.Placement = App.Placement(App.Vector(x_pos, y_pos, z_pos), direction, 90)

      self.bodies[label] = body

  def draw_plans(self):
    for label, body in self.bodies.items():
      link = doc.addObject('App::Link', f"link_cutout_{label}")
      link.setLink(body)
      link.Label = f"link_cutout_{label}"
      link.LinkTransform = True
      link.ViewObject.Visibility = False
      self.scratch.addObject(link)

      face = Draft.make_shape2dview(link, App.Vector(0, 0, 1))
      face.Label = f"face_{label}"
      self.plans.addObject(face)
      self.faces.append(face)

  def export_dxf(self):
    dimensions = doc.getObjectsByLabel("dimensions")[0]
    export_dxf = dimensions.get("export_dxf")
    if not export_dxf:
      return

    path = u"/home/duncan/Working/freecad_small_boat_hull/dingy.dxf"
    self.doc.recompute()
    importDXF.export(self.faces, path, lwPoly=True)


def has_object_by_label(doc, label):
  return label in [o.Label for o in FreeCAD.ActiveDocument.Objects]


def remove_group(doc, name):
  if not has_object_by_label(doc, name):
    return

  groups = doc.getObjectsByLabel(name)
  if not isinstance(groups, list):
    groups = [groups]

  for group in groups:
    if group:
      try:
        OpenSCADUtils.removesubtree(group)
      except TypeError:
        group.removeObjectsFromDocument()
        doc.removeObject(group.Name)


def create_group(doc, name, type_ = 'App::DocumentObjectGroup'):
  remove_group(doc, name)
  return doc.addObject(type_, name)


def addSelection(doc, label):
  if not has_object_by_label(doc, label):
    return
  Gui.Selection.addSelection(doc.Name, label)


def get_body():
  return App.ActiveDocument.getObject("hull")


def perpendicular(wire, position):
  """
  Calculate angle perpendicular to wire.
  Args:
    wire: Part.Wire: A FreeCAD wire.
    position: App.Vector: Position on wire to calculate angle at.
  Returns:
    Tuple:
      Angle perpendicular to wire.
      Position on Z axis line at angle passing through input position crosses.
        Used for projecting slicing plane.
  """
  for edge in wire.OrderedEdges:
    shapes = edge.Curve.toBiArcs(1)
    for shape in shapes:
      distance = shape.projectPoint(position, "Distance")
      if len(distance) == 1 and distance[0] < 0.1:
        if isinstance(shape, Part.ArcOfCircle):
          vector = shape.Location - position
        elif isinstance(shape, Part.LineSegment):
          vector = (shape.EndPoint - shape.StartPoint).cross(App.Vector(0, 1, 0))
        else:
          print(shape)
          continue

        vector.normalize()
        angle = vector.getAngle(App.Vector(0, 0, 1))
        print(angle, math.degrees(angle))
        angle += math.radians(10)

        z = position.z - position.x / math.tan(-angle)
        print(round(z, 2))

        return (angle, z)
  return None

def get_wire_ends(wire):
  """ Gets ends of a wire. Returns a list of any vertexes in a wire with only one connection. """
  sorted_edges = Part.sortEdges(wire.Edges)
  wire = Part.Wire(sorted_edges[0])
  end_points = []
  for vertex in wire.Vertexes:
      if len(wire.ancestorsOfType(vertex, Part.Edge)) == 1:
          end_points.append(vertex.Point)

  return end_points

def simplify_arcs(wire: Part.Wire) -> Part.Wire:
  """ Rewrite any Part::GeomOffsetCurve shapes as simple Arc and Lines."""
  modified_edges = []
  for edge in wire.Edges:
    if edge.Curve.TypeId == "Part::GeomOffsetCurve":
      for new in edge.Curve.toBSpline().toBiArcs(0.001):
        modified_edges.append(new.toShape())
    else:
      modified_edges.append(edge)
  modified_edges = Part.sortEdges(modified_edges)[0]
  return Part.Wire(modified_edges)

def get_wire_curvature(wire):
  ordered_vertexes = wire.OrderedVertexes
  a = ordered_vertexes[0].Point
  b = ordered_vertexes[int(len(ordered_vertexes) / 2)].Point
  c = ordered_vertexes[-1].Point
  curvature = (a -b).cross(b - c).z
  return curvature

def clean_wire(wire):
  """ Turn wire with Curves as edges into straight lines as edges. """
  edges = Part.sortEdges(wire.Edges)[0]

  # Fill gaps
  curves = []
  fill_missing = False
  for edge in edges:
    if edge.Curve.TypeId == "Part::GeomLine":
      fill_missing = True
    else:
      next_curve = edge.Curve
      if fill_missing:
        last_curve = curves[-1]
        points = [last_curve.EndPoint, next_curve.StartPoint]
        missing_curve = Part.BSplineCurve()
        missing_curve.interpolate(points)
        curves.append(missing_curve)
        fill_missing = False

      curves.append(next_curve)

  # Join all curves into one.
  combined_curve = None
  for curve in curves:
    if combined_curve is None:
      combined_curve = curve
    else:
      combined_curve.join(curve)

  #Part.show(combined_curve.toShape(), "combined_curve")

  # Split curve into Vertexes and make lines from them.
  last_point = None
  edges = []
  for point in combined_curve.discretize(Angular=0.5, Curvature=0.1):
    if last_point is not None:
      l = Part.LineSegment(last_point, point).toShape()
      if l.Length < 1:
        continue
      edges.append(l)
    last_point = point

  return Part.Wire(edges)

def clean_wire2(wire):
  edges = []
  start_point = None
  for index, edge in enumerate(wire.Edges):
    if start_point:
      edges.append(Part.LineSegment(start_point, edge.valueAt(edge.LastParameter)).toShape())
    else:
      edges.append(Part.LineSegment(edge.valueAt(edge.FirstParameter), edge.valueAt(edge.LastParameter)).toShape())
    start_point = edge.valueAt(edge.LastParameter)

  wire = Part.Wire(edges)
  return wire

def join_wires(wires: list[Part.Wire]) -> Part.Wire:
  return_values = []
  last_end = None
  for wire in wires:
    if isinstance(wire, Part.Edge):
      wire = Part.Wire(wire)

    if not last_end:
      last_end = wire
      continue

    if isinstance(last_end, Part.Wire):
      distances = [
        (0, 0, last_end.OrderedVertexes[0].Point.distanceToPoint(wire.OrderedVertexes[0].Point)),
        (-1, 0, last_end.OrderedVertexes[-1].Point.distanceToPoint(wire.OrderedVertexes[0].Point)),
        (0, -1, last_end.OrderedVertexes[0].Point.distanceToPoint(wire.OrderedVertexes[-1].Point)),
        (-1, -1, last_end.OrderedVertexes[-1].Point.distanceToPoint(wire.OrderedVertexes[-1].Point)),
        ]
      closest_ends = sorted(distances, key = lambda val: val[2])[0]
      if closest_ends[0] == 0:
        last_end.reverse()
      if closest_ends[1] == -1:
        wire.reverse()
      return_values.append(last_end)
      return_values.append(wire)
      last_end = wire.OrderedVertexes[-1].Point
      continue

    if last_end.distanceToPoint(wire.OrderedVertexes[-1].Point) < last_end.distanceToPoint(wire.OrderedVertexes[0].Point):
      wire.reverse()
    last_end = wire.OrderedVertexes[-1].Point
    return_values.append(wire)

  edges = []
  for wire in return_values:
    edges += wire.Edges

  return Part.Shape(edges).makeWires("outline")


doc = App.ActiveDocument
body = get_body()

start = time.perf_counter()
pr = cProfile.Profile()
pr.enable()

if body:
  data_x = Slice_Profile(doc, body, intersection_count = 5)
  View_Wireframe_Profile(body.Name, doc, body, data_x)

  data_y = Slice_Waterline(doc, body, intersection_count = 6)
  View_Wireframe_Waterline(body.Name, doc, body, data_y)

  data_z = Slice_CrossSection(doc, body)
  View_Wireframe_Body(body.Name, doc, body, data_z)

  data_xz = Slice_Diagonals(doc, body, data_z)
  View_Wireframe_Diagonals(body.Name, doc, body, data_xz)

  lowest_point = min(data_x.lowest_point, data_y.lowest_point, data_z.lowest_point)

  Plans(doc, body.Name, lowest_point)

  components = Components(doc, body.Name, body.Shape, data_xz)
  Layout(doc, components)
  Mass(doc, components)

else:
  print("No hull selected.")

Gui.Selection.clearSelection()
Gui.Selection.addSelection(doc.Name, body.Name)

pr.disable()
pr.dump_stats("profile.cprof")
end = time.perf_counter()
print(f"Took {end - start} seconds")
