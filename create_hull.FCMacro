# vim: set ft=python :
# vim: set expandtab :

import pdb
import math
import time
#import cProfile

import FreeCAD as App
import Part
import Sketcher
from FreeCAD import Vector
from FreeCAD import Units
from PySide import QtGui
import DraftGeomUtils

def start_():
    label = "hull"
    doc = App.ActiveDocument or App.newDocument()
    body = doc.addObject('PartDesign::Body', label)
    body_hollow = doc.addObject('PartDesign::Body', f"{label}_hollow")

    assert body.Name.startswith(label)
    hull_index = 0
    if label != body.Name:
      hull_index = int(body.Name[len(label):])

    origin = body.OutList[0]
    plane = [p for p in origin.OutList if "XZ" in p.Name][0]

    return (doc, body, body_hollow, hull_index, plane)

def make_hull_sections(doc, body, hull_index, plane):
    dimensions = doc.getObjectsByLabel('dimensions')[0]

    deck_length = dimensions.deck_length
    deck_width = dimensions.deck_width
    highest = dimensions.deck_height + dimensions.prow_height
    lowest = -1.0
    section_count = dimensions.section_count
    step_len = (deck_length - Units.Quantity("2mm")) / (section_count - 1)

    # Templates outlining hull shape.
    sketch_profile_deck = doc.getObjectsByLabel('profile_deck')[0]
    sketch_profile_keel = doc.getObjectsByLabel('profile_keel')[0]
    sketch_plan_deck = doc.getObjectsByLabel('plan_deck')[0]
    # These 2 dictate the centre of the arc used to form the curve from the top
    # of the hull deadrise to the deck.
    sketch_hull_curve_height = doc.getObjectsByLabel('hull_curve_height')[0]
    sketch_hull_curve_horizontal = doc.getObjectsByLabel('hull_curve_horizontal')[0]

    cross_sections = []

    section_pos = -deck_length / 2 + Units.Quantity("1mm")
    index = 0
    while round(section_pos) <= round(deck_length / 2):
      print(index, round(section_pos, 2))

      section_name = f"section_{index}"
      #print(f"Creating {section_name} at {section_pos}.")

      # Plane for calculating intersections.
      intersection_plane = Part.makePlane(highest * 2, deck_width * 2, App.Vector(-deck_width, -section_pos, 0), App.Vector(0, 1, 0))
      #Part.show(intersection_plane, f"plane_{index}")

      deck_plan_intersection = get_intersection(sketch_plan_deck, intersection_plane, section_pos)
      deck_height_intersection = get_intersection(sketch_profile_deck, intersection_plane, section_pos)
      keel_height_intersection = get_intersection(sketch_profile_keel, intersection_plane, section_pos)
      hull_curve_height_intersection = get_intersection(sketch_hull_curve_height, intersection_plane, section_pos)
      hull_curve_horizontal_intersection = get_intersection(sketch_hull_curve_horizontal, intersection_plane, section_pos)

      section = make_section(
        body, hull_index, section_name, section_pos,
        plane, deck_plan_intersection, deck_height_intersection, keel_height_intersection,
        hull_curve_height_intersection, hull_curve_horizontal_intersection)

      section = simplify_section(section, section_pos,
				 deck_plan_intersection, deck_height_intersection,
				 keel_height_intersection)

      cross_sections.append((section_pos, section))

      section_pos += step_len
      index += 1

    return cross_sections

def make_section(body, hull_index, name, z, plane, deck_plan, deck_height, keel_height, hull_curve_height, hull_curve_horizontal):
  """Create geometry for the hull's cross-section at a specific point between bow and stern."""
  sketch = body.newObject("Sketcher::SketchObject", name)
  #sketch.AttachmentOffset = App.Placement(App.Vector(0, 0, z + hull_index * 4000), App.Rotation(App.Vector(0, 0, 1), 0))
  sketch.AttachmentOffset = App.Placement(App.Vector(0, hull_index * 2000, z), App.Rotation(App.Vector(0, 0, 1), 0))
  sketch.AttachmentSupport = (plane, [''])
  sketch.MapMode = 'FlatFace'
  sketch.Visibility = False

  geoList = []
  constraintList = []

  # Starboard
  geoList.append(Part.LineSegment(App.Vector(0.0, 0.0, 0.0), App.Vector(-500.0, 50.0, 0.0)))
  geoList.append(Part.ArcOfCircle(Part.Circle(App.Vector(-474.527130, 540.000000, 0.0), App.Vector(0.000000, 0.000000, 1.000000), 482.076102), 3.159565, 4.597564))

  constraintList.append(Sketcher.Constraint('DistanceX', -1, 1, 0, 1, 0.0))
  constraintList.append(Sketcher.Constraint('Tangent', 1, 2, 0, 2))
  constraintList.append(Sketcher.Constraint('DistanceY', 1, 1, deck_height.Z))
  constraintList.append(Sketcher.Constraint('DistanceY', 0, 1, keel_height.Z))
  constraintList.append(Sketcher.Constraint('DistanceX', 1, 1, deck_plan.X))
  constraintList.append(Sketcher.Constraint('DistanceX', 1, 3, hull_curve_horizontal.X))
  constraintList.append(Sketcher.Constraint('DistanceY', 1, 3, hull_curve_height.Z))

  # Port
  geoList.append(Part.LineSegment(App.Vector(0.0, 0.0, 0.0), App.Vector(500.0, 50.0, 0.0)))
  geoList.append(Part.ArcOfCircle(Part.Circle(App.Vector(474.527130, 540.000000, 0.0), App.Vector(0.000000, 0.000000, 1.000000), 472.076102), 4.6, 6))

  constraintList.append(Sketcher.Constraint('DistanceX', -1, 1, 2, 1, 0.0))
  constraintList.append(Sketcher.Constraint('Tangent', 2, 2, 3, 1))
  constraintList.append(Sketcher.Constraint('DistanceY', 3, 2, deck_height.Z))
  constraintList.append(Sketcher.Constraint('DistanceY', 2, 1, keel_height.Z))
  constraintList.append(Sketcher.Constraint('DistanceX', 3, 2, -deck_plan.X))
  constraintList.append(Sketcher.Constraint('DistanceX', 3, 3, -hull_curve_horizontal.X))
  constraintList.append(Sketcher.Constraint('DistanceY', 3, 3, hull_curve_height.Z))

  # Deck
  geoList.append(Part.LineSegment(App.Vector(-500.0, 500.0, 0.0), App.Vector(500.0, 500.0, 0.0)))

  constraintList.append(Sketcher.Constraint('DistanceX', 4, 0, -deck_plan.X * 2))
  constraintList.append(Sketcher.Constraint('DistanceX', 4, 1, deck_plan.X))
  constraintList.append(Sketcher.Constraint('DistanceY', 4, 0, 0.0))
  constraintList.append(Sketcher.Constraint('DistanceY', 4, 1, deck_height.Z))

  sketch.addGeometry(geoList, False)
  sketch.addConstraint(constraintList)

  return sketch

def simplify_section(sketch, z, deck_plan, deck_height, keel_height):
  """Check if hull's deadrise crosses above the gunwale, making the arc in the geometry unnecessary (and troublesome)."""
  sketch.recompute()
  if sketch.Shape.Edges and not abs(
      sketch.Shape.Edges[1].LastParameter - sketch.Shape.Edges[1].FirstParameter) > math.pi:
    return sketch

  #print(f"Simplifying section at {z}. {sketch.Name}.")
  sketch.deleteAllConstraints()
  sketch.deleteAllGeometry()

  geoList = []
  constraintList = []

  # Starboard
  geoList.append(Part.LineSegment(App.Vector(0.0, 0.0, 0.0), App.Vector(-250.0, 250.0, 0.0)))
  geoList.append(Part.LineSegment(App.Vector(-250.0, 250.0, 0.0), App.Vector(-500.0, 500.0, 0.0)))
  
  start = App.Vector(0, keel_height.Z, 0)
  end = App.Vector(deck_plan.X, deck_height.Z, 0)
  vector = end - start
  split = start + (99 * vector / 100)

  constraintList.append(Sketcher.Constraint('DistanceX', -1, 1, 0, 1, 0.0))
  constraintList.append(Sketcher.Constraint('DistanceY', 0, 1, keel_height.Z))

  constraintList.append(Sketcher.Constraint('DistanceX', 0, 2, split.x))
  constraintList.append(Sketcher.Constraint('DistanceY', 0, 2, split.y))
  constraintList.append(Sketcher.Constraint('DistanceX', 1, 1, split.x))
  constraintList.append(Sketcher.Constraint('DistanceY', 1, 1, split.y))
  
  constraintList.append(Sketcher.Constraint('DistanceX', 1, 2, deck_plan.X))
  constraintList.append(Sketcher.Constraint('DistanceY', 1, 2, deck_height.Z))
  
  # Port
  geoList.append(Part.LineSegment(App.Vector(0.0, 0.0, 0.0), App.Vector(250.0, 250.0, 0.0)))
  geoList.append(Part.LineSegment(App.Vector(250.0, 250.0, 0.0), App.Vector(500.0, 500.0, 0.0)))
  constraintList.append(Sketcher.Constraint('DistanceX', -1, 1, 2, 1, 0.0))
  constraintList.append(Sketcher.Constraint('DistanceY', 2, 1, keel_height.Z))

  constraintList.append(Sketcher.Constraint('DistanceX', 2, 2, -split.x))
  constraintList.append(Sketcher.Constraint('DistanceY', 2, 2, split.y))
  constraintList.append(Sketcher.Constraint('DistanceX', 3, 1, -split.x))
  constraintList.append(Sketcher.Constraint('DistanceY', 3, 1, split.y))
  
  constraintList.append(Sketcher.Constraint('DistanceX', 3, 2, -deck_plan.X))
  constraintList.append(Sketcher.Constraint('DistanceY', 3, 2, deck_height.Z))

  # Deck
  geoList.append(Part.LineSegment(App.Vector(-500.0, 500.0, 0.0), App.Vector(500.0, 500.0, 0.0)))

  constraintList.append(Sketcher.Constraint('DistanceX', 4, 1, deck_plan.X))
  constraintList.append(Sketcher.Constraint('DistanceX', 4, 0, -deck_plan.X * 2))
  constraintList.append(Sketcher.Constraint('DistanceY', 4, 0, 0.0))
  constraintList.append(Sketcher.Constraint('DistanceY', 4, 1, deck_height.Z))
  
  sketch.addGeometry(geoList, False)
  sketch.addConstraint(constraintList)

  sketch.recompute()

  return sketch

def make_section_hollow(section, position, body_hollow, plane):
  new_sketch = body_hollow.newObject("Sketcher::SketchObject", f"{section.Name}_hollow")
  new_sketch.AttachmentOffset = App.Placement(App.Vector(0, hull_index * 2000, position), App.Rotation(App.Vector(0, 0, 1), 0))
  new_sketch.AttachmentSupport = (plane, [''])
  new_sketch.MapMode = 'FlatFace'
  new_sketch.Visibility = False

  geoList = []
  for shape in section.Geometry:
    if shape.EndPoint.y == shape.StartPoint.y:
      # Deck. To be skipped for open topped hull shell.
      continue
    geoList.append(shape.copy())

  hullThickness = 5
  moreGeoList = []
  highest_shape = None
  highest_more = None
  highest_port = [0, []]
  highest_starboard = [0, []]
  for shape in geoList:
    if isinstance(shape, Part.ArcOfCircle):
      moreGeoList.append(
	  Part.ArcOfCircle(
	    Part.Circle(shape.Location, App.Vector(0, 0, 1), shape.Radius + hullThickness),
	    shape.FirstParameter, shape.LastParameter)
      )
    elif isinstance(shape, Part.LineSegment):
      join_bottom = False
      vector = (shape.EndPoint - shape.StartPoint).cross(App.Vector(0, 0, 1))
      if vector.Length:
        vector = vector.normalize()
      if shape.StartPoint.x == 0 or shape.EndPoint.x == 0:
        if shape.EndPoint.x < 0 or shape.StartPoint.x < 0:
          join_bottom = True
      if shape.EndPoint.x < 0 or shape.StartPoint.x < 0:
        vector = vector.negative()

      moreGeoList.append(
	  Part.LineSegment(shape.StartPoint + vector * hullThickness, shape.EndPoint + vector * hullThickness)
      )

      if join_bottom:
        if shape.EndPoint.x == 0:
          center = shape.EndPoint
        else:
          center = shape.StartPoint
        moreGeoList.append(
            Part.ArcOfCircle(
              Part.Circle(center, App.Vector(0, 0, 1), hullThickness),
              -vector.getAngle(App.Vector(1, 0, 0)),
              math.pi + vector.getAngle(App.Vector(1, 0, 0))
            )
        )

    highest = highest_end(shape)
    height = highest.y
    if height > highest_port[0] and highest.x < 0:
        highest_port = [height, (shape, moreGeoList[-1])]
    if height > highest_starboard[0] and highest.x >= 0:
        highest_starboard = [height, (shape, moreGeoList[-1])]

  moreGeoList.append(Part.LineSegment(highest_end(highest_port[1][0]), highest_end(highest_port[1][1])))
  moreGeoList.append(Part.LineSegment(highest_end(highest_starboard[1][0]), highest_end(highest_starboard[1][1])))
  
  new_sketch.addGeometry(geoList + moreGeoList, False)

  return new_sketch

def highest_end(shape):
  return max(shape.StartPoint, shape.EndPoint, key = lambda val : val.y)

def draw(sections, hull_index, body):
    additive_loft = body.newObject('PartDesign::AdditiveLoft', f"hull_loft_{hull_index}")
    additive_loft.Ruled = True

    for _, cross_section in cross_sections:
      if not additive_loft.Profile:
        additive_loft.Profile = cross_section
      else:
        additive_loft.Sections += [cross_section]

def draw_hollow(cross_sections, hull_index, body_hollow, plane):
    additive_loft = body_hollow.newObject('PartDesign::AdditiveLoft', f"hull_loft_hollow_{hull_index}")
    additive_loft.Ruled = True

    for position, cross_section in cross_sections:
      new_sketch = make_section_hollow(cross_section, position, body_hollow, plane)
      if not additive_loft.Profile:
        additive_loft.Profile = new_sketch
      else:
        additive_loft.Sections += [new_sketch]

def get_intersection(sketch, plane, pos):
  for edge in sketch.Shape.Edges:
    points = plane.Surface.intersect(edge.Curve)
    #points = edge.slice(App.Vector(0, 1, 0), pos)
    if not points:
      continue
    for point in points[0]:
      if (plane.isInside(Vector(point.X, point.Y, point.Z), 0.01, True) and 
	  edge.isInside(Vector(point.X, point.Y, point.Z), 0.01, True)):
        return point
  return None


start = time.perf_counter()
#pr = cProfile.Profile()
#pr.enable()

doc, body, body_hollow, hull_index, plane= start_()
cross_sections = make_hull_sections(doc, body, hull_index, plane)
draw(cross_sections, hull_index, body)
draw_hollow(cross_sections, hull_index, body_hollow, plane)

#pr.disable()
#pr.dump_stats("profile.cprof")
end = time.perf_counter()
print(f"Took {end - start} seconds")
